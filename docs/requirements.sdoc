[DOCUMENT]
TITLE: Safe Kiln Controller, Requirements Specification
UID: SAFEKILN-SRS
VERSION: 0.1 (draft)
DATE: 2026-09-26
OPTIONS:
  MARKUP: Markdown
  VIEW_STYLE: Table
  NODE_IN_TOC: True
METADATA:
  SPDX-FileCopyrightText: 2026 Bitcrush Testing
  SPDX-License-Identifier: GPL-3.0-or-later
  Status: For review
  Project: Safe Kiln Controller, PID kiln controller

[GRAMMAR]
ELEMENTS:
- TAG: TEXT
  FIELDS:
  - TITLE: STATEMENT
    TYPE: String
    REQUIRED: True
- TAG: SECTION
  PROPERTIES:
    IS_COMPOSITE: True
  FIELDS:
  - TITLE: UID
    TYPE: String
    REQUIRED: False
  - TITLE: TITLE
    TYPE: String
    REQUIRED: True
- TAG: REQUIREMENT
  FIELDS:
  - TITLE: UID
    TYPE: String
    REQUIRED: True
  - TITLE: STATEMENT
    TYPE: String
    REQUIRED: True
  - TITLE: PRIORITY
    TYPE: SingleChoice(M, S, C, W)
    REQUIRED: False
  - TITLE: VERIFICATION
    TYPE: MultipleChoice(T, A, I, D)
    REQUIRED: False
  - TITLE: STATUS
    TYPE: SingleChoice(Active, Withdrawn, Superseded, Reversed, Resolved)
    REQUIRED: False
  RELATIONS:
  - TYPE: Parent
- TAG: CONSTRAINT
  FIELDS:
  - TITLE: UID
    TYPE: String
    REQUIRED: True
  - TITLE: STATEMENT
    TYPE: String
    REQUIRED: True
  - TITLE: STATUS
    TYPE: SingleChoice(Active, Withdrawn, Superseded, Reversed, Resolved)
    REQUIRED: False
- TAG: ASSUMPTION
  FIELDS:
  - TITLE: UID
    TYPE: String
    REQUIRED: True
  - TITLE: STATEMENT
    TYPE: String
    REQUIRED: True
  - TITLE: STATUS
    TYPE: SingleChoice(Active, Withdrawn, Superseded, Reversed, Resolved)
    REQUIRED: False
- TAG: QUESTION
  FIELDS:
  - TITLE: UID
    TYPE: String
    REQUIRED: True
  - TITLE: STATEMENT
    TYPE: String
    REQUIRED: True
  - TITLE: STATUS
    TYPE: SingleChoice(Active, Withdrawn, Superseded, Reversed, Resolved)
    REQUIRED: False

[[SECTION]]
UID: SECT-1
TITLE: 1. Introduction

[[SECTION]]
UID: SECT-1-1
TITLE: 1.1 Purpose

[TEXT]
STATEMENT: >>>
This document specifies the requirements for **Safe Kiln Controller**, an open-source
temperature controller for electric ceramic / glass kilns. It is the reference
for implementation, verification and review. The software architecture derived
from this document is [`architecture.md`](architecture.md).
<<<

[[/SECTION]]

[[SECTION]]
UID: SECT-1-2
TITLE: 1.2 Scope

[TEXT]
STATEMENT: >>>
Safe Kiln Controller replaces the mechanical or simple on/off controller of an electric
kiln with a closed-loop PID controller that follows a user-defined
**firing curve** (a time/temperature program). The operator interacts with the
device through a small local display and, over WiFi, through a built-in web
interface that also visualises logged temperature data.

In scope:

- Temperature acquisition from a type-K thermocouple in the kiln chamber, plus a
  second thermocouple for enclosure/electronics temperature.
- Time-proportional PID control of a solid-state relay switching the heating
  elements, with an independent safety contactor.
- Measurement of heater current with a current transformer (Stromwandler), for
  direct electrical detection of a failed relay, contactor or heating element.
- Automatic PID tuning against the real kiln.
- Storage and execution of multi-segment firing programs.
- Local display of current and target temperature plus program state.
- A self-hosted web interface for program editing, live monitoring, historical
  temperature charts and configuration.
- On-device logging of every firing run without an SD card or external database.
- Safety supervision: thermal runaway, sensor failure, relay failure,
  over-temperature.

Out of scope: see §12 ([LINK: SECT-12]).
<<<

[[/SECTION]]

[[SECTION]]
UID: SECT-1-3
TITLE: 1.3 Definitions and abbreviations

[TEXT]
STATEMENT: >>>
| Term | Meaning |
|---|---|
| **Firing program** | Ordered list of segments describing a complete firing. Also "curve", "profile", "schedule". |
| **Segment** | One element of a program: ramp to a target temperature at a given rate, then dwell (hold) for a given time. |
| **Setpoint (SP)** | The instantaneous temperature the controller is aiming for. Produced by the setpoint generator from the active program; it is *not* the segment target except at the end of a ramp. |
| **Process value (PV)** | The measured kiln temperature. |
| **Control output (CV)** | PID output, 0–100 % heating duty. |
| **Dwell / soak** | Holding the temperature constant for a defined time. |
| **Ramp rate** | Rate of change of the setpoint, in °C/h. |
| **Hold-back** | Suspension of setpoint advance while PV lags SP beyond a threshold, so a slow kiln cannot silently fall behind its curve. |
| **SSR** | Solid-state relay. Modulates heater power. |
| **Contactor / EMR** | Electromechanical relay or contactor in series with the SSR. Provides a galvanic break independent of the SSR. |
| **TC** | Thermocouple. |
| **CJC** | Cold-junction compensation. |
| **Stromwandler / CT** | Current transformer. A split-core clip-on transformer around one heater conductor giving a galvanically isolated signal proportional to heater current. |
| **Burden** | The resistor across a CT secondary that turns its output current into a voltage. A current-output CT whose burden is removed while primary current flows develops dangerous open-circuit voltages. |
| **RMS** | Root mean square: the heating-equivalent value of an alternating waveform. |
| **Fail-on / fail-off** | A switching device stuck conducting (fail-on) or stuck open (fail-off). A shorted SSR and a welded contactor are both fail-on faults. |
| **Weld discrimination** | Determining whether unexpected current is due to a shorted SSR or a welded contactor, by dropping the contactor and re-measuring. |
| **Time-proportional control** | Converting a 0–100 % duty into on/off intervals within a fixed window, since an SSR cannot be driven at an analogue level. |
| **Relay autotune** | Åström–Hägglund method: force a bounded limit cycle with on/off control, measure its amplitude and period, derive PID gains. |
| **HAL** | Hardware abstraction layer. |
| **HIL** | Hardware in the loop. |
| **SUT** | System under test. |
| **NVS** | ESP-IDF Non-Volatile Storage (key/value store in flash). |
<<<

[[/SECTION]]

[[SECTION]]
UID: SECT-1-4
TITLE: 1.4 Requirement conventions

[TEXT]
STATEMENT: >>>
Each requirement has a stable identifier, a **shall** statement, and a
verification method:

| Code | Method | Meaning |
|---|---|---|
| **T** | Test | Automated test (host unit test, target test, or HIL test). |
| **A** | Analysis | Calculation, model, static analysis or code metric. |
| **I** | Inspection | Review of code, schematic or document. |
| **D** | Demonstration | Operating the system and observing behaviour. |

Priority: **M** = mandatory for v1.0, **S** = should have, **C** = could have
(deferred without blocking release).

Identifier prefixes:

| Prefix | Area |
|---|---|
| `ASM` | Assumption |
| `CON` | Constraint |
| `FR-ACQ` | Temperature acquisition |
| `FR-CTL` | Control loop |
| `FR-TUN` | Automatic PID tuning |
| `FR-PRG` | Firing programs |
| `FR-RUN` | Run control and state machine |
| `FR-HMI` | Local display and input |
| `FR-WEB` | Web interface |
| `FR-LOG` | Data logging |
| `FR-CFG` | Configuration |
| `FR-NET` | Connectivity and time |
| `FR-UPD` | Firmware update |
| `SR` | Safety requirement |
| `NFR` | Non-functional requirement |
| `HR` | Hardware interface requirement |
| `TR` | Testability requirement |
<<<

[[/SECTION]]

[[SECTION]]
UID: SECT-1-5
TITLE: 1.5 References

[TEXT]
STATEMENT: >>>
| Ref | Document |
|---|---|
| [R1] | [PIDKiln](https://github.com/Saur0o0n/PIDKiln) by Adrian Siemieniak, ESP32 kiln controller, the functional inspiration for this project (GPL-3.0). |
| [R2] | Espressif, *ESP-IDF Programming Guide*, v5.x. |
| [R3] | Analog Devices, *MAX31856 Precision Thermocouple to Digital Converter with Linearization*, datasheet. |
| [R4] | IEC 60584-1, *Thermocouples, Part 1: EMF specifications and tolerances*. |
| [R5] | K. J. Åström, T. Hägglund, *PID Controllers: Theory, Design and Tuning*, 2nd ed., 1995. |
| [R6] | IEC 60519-1, *Safety in installations for electroheating and electromagnetic processing*. |
| [R7] | GNU General Public License version 3, [`../LICENSE`](../LICENSE). |
<<<

[[/SECTION]]

[[SECTION]]
UID: SECT-1-6
TITLE: 1.6 Relationship to PIDKiln

[TEXT]
STATEMENT: >>>
PIDKiln [R1] demonstrates that a ~40 USD ESP32 board can run a real kiln, and
this project adopts its proven ideas: a segment-based program model
(`target / ramp / dwell`), dual display and web control, on-device storage with
no external services, a redundant SSR + contactor output stage, and safety
supervision covering runaway, probe failure, SSR failure and insulation
degradation.

Safe Kiln Controller deliberately diverges in the following respects, and these
divergences drive many requirements below:

| Aspect | PIDKiln | Safe Kiln Controller | Driver |
|---|---|---|---|
| Framework | Arduino-ESP32 | ESP-IDF v5.x ([LINK: CON-01]) | Explicit requirement; better test tooling, partition/OTA control, watchdogs |
| MCU | ESP32-WROVER | ESP32-S3 ([LINK: HR-01]) | Explicit requirement |
| TC front-end | MAX31855 (K only, ≤1350 °C) | MAX31856 (K/N/S/R/B/E/J/T, richer fault detection) | Diagnosability, [LINK: SR-04] |
| PID gains | Manually tuned, documented by experiment | Automatic tuning on-device (FR-TUN ([LINK: SECT-3-3])) | Explicit requirement |
| Storage | SPIFFS on internal flash, microSD board recommended | Dedicated raw partitions, fixed slots for programs and run records and a circular ring for the log, no SD card and no filesystem ([LINK: CON-03]) | Explicit requirement |
| Heater current | Optional 30 A/1 V power meter, not used for protection | **Mandatory** current transformer driving relay fail-on / fail-off detection and weld discrimination (FR-CUR ([LINK: SECT-3-12]), [LINK: SR-25]–[LINK: SR-30]) | Explicit requirement; resolves [LINK: OQ-02] |
| Architecture | Arduino sketch, hardware access throughout | Layered, HAL-isolated, host-testable core (TR ([LINK: SECT-7])) | Explicit requirement: design for testability |

No PIDKiln source code is copied. Safe Kiln Controller is licensed GPL-3.0-or-later, the
same licence as PIDKiln, so derivation remains possible in either direction.
<<<

[[/SECTION]]

[[/SECTION]]

[[SECTION]]
UID: SECT-2
TITLE: 2. System overview

[[SECTION]]
UID: SECT-2-1
TITLE: 2.1 Context

[TEXT]
STATEMENT: >>>
```mermaid
flowchart LR
    OP(["Operator"])
    subgraph KC["Safe Kiln Controller device"]
        MCU["ESP32-S3<br/>controller"]
        OLED["128x64 OLED"]
        ENC["Encoder<br/>+ button"]
        BUZ["Buzzer"]
    end
    subgraph KILN["Kiln"]
        TC1["Chamber<br/>thermocouple"]
        ELEM["Heating<br/>elements"]
    end
    SSR["SSR"]
    CONT["Safety<br/>contactor"]
    CT["Current<br/>transformer"]
    TC2["Enclosure<br/>thermocouple"]
    BROWSER(["Browser on<br/>phone / PC"])
    MAINS(["Mains supply"])

    OP -->|turn / press| ENC
    OLED -->|temperatures, state| OP
    BUZ -->|alarm| OP
    TC1 -->|mV| MCU
    TC2 -->|mV| MCU
    MCU -->|duty| SSR
    MCU -->|heat enable| CONT
    MAINS --> CONT --> SSR --> CT --> ELEM
    CT -->|heater current| MCU
    ELEM -.->|heat| TC1
    MCU <-->|WiFi / HTTP| BROWSER
```
<<<

[[/SECTION]]

[[SECTION]]
UID: SECT-2-2
TITLE: 2.2 Operating modes

[TEXT]
STATEMENT: >>>
```mermaid
stateDiagram-v2
    [*] --> Idle
    Idle --> RunningProgram: start program
    Idle --> Manual: set fixed target
    Idle --> Autotune: start tuning
    RunningProgram --> Paused: pause
    Paused --> RunningProgram: resume
    RunningProgram --> Complete: last segment done
    Manual --> Idle: stop
    Autotune --> Idle: finished / aborted
    Complete --> Idle: acknowledge
    RunningProgram --> Fault: safety trip
    Manual --> Fault: safety trip
    Autotune --> Fault: safety trip
    Paused --> Fault: safety trip
    Fault --> Idle: acknowledge (heat off, cooled)
```

| Mode | Description |
|---|---|
| **Idle** | Heating disabled, temperature monitored and displayed. |
| **Running** | Executing a firing program under PID control. |
| **Paused** | Program suspended, heating off, elapsed time frozen; resumable. |
| **Manual** | PID holds a single operator-entered target temperature indefinitely. |
| **Autotune** | Automatic PID tuning procedure in progress. |
| **Complete** | Program finished normally; cooling, awaiting acknowledgement. |
| **Fault** | A safety condition tripped. Heating de-energised and latched off. |
<<<

[[/SECTION]]

[[SECTION]]
UID: SECT-2-3
TITLE: 2.3 Primary use cases

[TEXT]
STATEMENT: >>>
| UC | Actor | Description |
|---|---|---|
| UC-1 | Operator | Load a stored firing program, review it, start it, and walk away. |
| UC-2 | Operator | Watch current vs. target temperature on the local display. |
| UC-3 | Operator | Open the web interface on a phone to see live status and the curve traced so far. |
| UC-4 | Operator | Create or edit a firing program in the browser and save it on the device. |
| UC-5 | Operator | Change the target temperature or ramp of a *running* program. |
| UC-6 | Operator | Abort a running firing from either the device or the browser. |
| UC-7 | Operator | Run automatic PID tuning after installing the controller on a new kiln. |
| UC-8 | Operator | Review the logged temperature trace of a previous firing and export it. |
| UC-9 | System | Detect a failed element, shorted SSR, welded contactor or broken thermocouple, de-energise the kiln and alarm. |
| UC-12 | Operator | Fit a clip-on current transformer to a heater conductor and calibrate it against a reference meter. |
| UC-13 | Operator | See that this firing is drawing less current than usual and conclude an element is failing, before it ruins a load. |
| UC-10 | Installer | Provision WiFi credentials and configure kiln limits on first power-up. |
| UC-11 | Maintainer | Update firmware over WiFi. |
<<<

[[/SECTION]]

[[/SECTION]]

[[SECTION]]
UID: SECT-3
TITLE: 3. Functional requirements

[[SECTION]]
UID: SECT-3-1
TITLE: 3.1 Temperature acquisition (FR-ACQ)

[REQUIREMENT]
UID: FR-ACQ-01
STATEMENT: >>>
The system shall measure chamber temperature with a MAX31856 thermocouple front-end over SPI.
<<<
PRIORITY: M
VERIFICATION: T

[REQUIREMENT]
UID: FR-ACQ-02
STATEMENT: >>>
The **chamber** thermocouple shall be type **K**, and its type shall not be configurable.

The chamber front end is read by the independent safety supervisor, which applies a hard-coded temperature backstop ([LINK: SR-23]). The MAX31856 linearises according to a type register, so whoever sets that register determines what the supervisor's temperature *means*: with the supervisor expecting type K and a type S couple fitted, the reading at 1300 °C is roughly a quarter of type K's output and the backstop would never fire. Tripping on raw thermovoltage does not escape this, because a threshold set for the least sensitive type never fires for the most sensitive and one set for the most sensitive fires at a few hundred degrees for the rest.

The other types are therefore a documented limitation of the supervised product rather than a silent hazard. The **enclosure** channel's type remains configurable, that channel not being in the supervisor's remit.
<<<
PRIORITY: M
VERIFICATION: T

[REQUIREMENT]
UID: FR-ACQ-03
STATEMENT: >>>
The system shall acquire chamber temperature at a rate of at least **4 Hz**, and the acquisition period shall be constant to within ±10 %.
<<<
PRIORITY: M
VERIFICATION: T

[REQUIREMENT]
UID: FR-ACQ-04
STATEMENT: >>>
The system shall apply cold-junction compensation using the MAX31856 internal cold-junction sensor.
<<<
PRIORITY: M
VERIFICATION: T

[REQUIREMENT]
UID: FR-ACQ-05
STATEMENT: >>>
The system shall report chamber temperature with a resolution of **0.1 °C** or finer and a usable range of **−20 °C to 1350 °C** for type K.
<<<
PRIORITY: M
VERIFICATION: T

[REQUIREMENT]
UID: FR-ACQ-06
STATEMENT: >>>
The system shall configure the front-end's line-frequency notch filter to **50 Hz or 60 Hz** according to configuration, defaulting to 50 Hz.
<<<
PRIORITY: M
VERIFICATION: T

[REQUIREMENT]
UID: FR-ACQ-07
STATEMENT: >>>
The system shall apply a configurable first-order low-pass filter to the measurement used for control, with a time constant of 0–30 s (default 2 s), and shall log the *unfiltered* value alongside it.
<<<
PRIORITY: S
VERIFICATION: T

[REQUIREMENT]
UID: FR-ACQ-08
STATEMENT: >>>
The system shall apply a configurable calibration offset of −50.0 … +50.0 °C and a gain factor of 0.90 … 1.10 to the chamber reading.
<<<
PRIORITY: S
VERIFICATION: T

[REQUIREMENT]
UID: FR-ACQ-09
STATEMENT: >>>
The system shall measure enclosure/electronics temperature with a second, independently configurable thermocouple channel.
<<<
PRIORITY: M
VERIFICATION: T

[REQUIREMENT]
UID: FR-ACQ-10
STATEMENT: >>>
The system shall read and expose the front-end fault register on every conversion, distinguishing at minimum: open circuit, short to VCC, short to GND, cold-junction out of range, thermocouple out of range, over/under-voltage.
<<<
PRIORITY: M
VERIFICATION: T

[REQUIREMENT]
UID: FR-ACQ-11
STATEMENT: >>>
The system shall compute the rate of temperature change (°C/h) from a regression over a configurable window of 10–300 s (default 60 s).
<<<
PRIORITY: M
VERIFICATION: T

[REQUIREMENT]
UID: FR-ACQ-12
STATEMENT: >>>
On a transient acquisition error the system shall retain the last valid reading for a configurable grace period of 1–30 s (default 5 s) before declaring a sensor fault ([LINK: SR-04]).
<<<
PRIORITY: M
VERIFICATION: T

[[/SECTION]]

[[SECTION]]
UID: SECT-3-2
TITLE: 3.2 Control loop (FR-CTL)

[REQUIREMENT]
UID: FR-CTL-01
STATEMENT: >>>
The system shall implement a PID controller producing a heating duty in the range 0–100 %.
<<<
PRIORITY: M
VERIFICATION: T

[REQUIREMENT]
UID: FR-CTL-02
STATEMENT: >>>
The controller shall execute at a fixed, configurable period of 0.25–5 s (default 1 s), independent of the acquisition rate.
<<<
PRIORITY: M
VERIFICATION: T

[REQUIREMENT]
UID: FR-CTL-03
STATEMENT: >>>
The controller shall use configurable gains Kp, Ki, Kd with the ranges and units defined in [LINK: FR-CFG-02].
<<<
PRIORITY: M
VERIFICATION: T

[REQUIREMENT]
UID: FR-CTL-04
STATEMENT: >>>
The controller shall compute the derivative term from the *measurement*, not the error, so that a setpoint step does not produce a derivative kick.
<<<
PRIORITY: M
VERIFICATION: T

[REQUIREMENT]
UID: FR-CTL-05
STATEMENT: >>>
The controller shall clamp its integral term and shall suspend integration while the output is saturated (conditional-integration anti-windup).
<<<
PRIORITY: M
VERIFICATION: T

[REQUIREMENT]
UID: FR-CTL-06
STATEMENT: >>>
On entering or leaving manual/automatic control the controller shall transfer bumplessly: the output shall not step by more than 1 % as a direct result of the mode change.
<<<
PRIORITY: S
VERIFICATION: T

[REQUIREMENT]
UID: FR-CTL-07
STATEMENT: >>>
The system shall convert duty to heater switching by **time-proportional control** over a configurable window of 0.5–30 s (default 2 s).
<<<
PRIORITY: M
VERIFICATION: T

[REQUIREMENT]
UID: FR-CTL-08
STATEMENT: >>>
The system shall enforce a configurable minimum on-time and minimum off-time (0–2000 ms, default 100 ms) and shall round a duty that cannot satisfy them to fully off or fully on.
<<<
PRIORITY: M
VERIFICATION: T

[REQUIREMENT]
UID: FR-CTL-09
STATEMENT: >>>
The system shall generate the setpoint from the active program by linear interpolation in time, so that the setpoint advances at the segment's ramp rate rather than stepping to the segment target.
<<<
PRIORITY: M
VERIFICATION: T

[REQUIREMENT]
UID: FR-CTL-10
STATEMENT: >>>
The system shall support a ramp rate of 1–9999 °C/h, where a configured rate of **0 means "as fast as the kiln allows"** (setpoint follows the segment target directly).
<<<
PRIORITY: M
VERIFICATION: T

[REQUIREMENT]
UID: FR-CTL-11
STATEMENT: >>>
The system shall implement **hold-back**: when |SP − PV| exceeds a configurable band (0–200 °C, default 0 disables), the setpoint shall stop advancing and the segment timer shall pause until PV re-enters the band.
<<<
PRIORITY: M
VERIFICATION: T

[REQUIREMENT]
UID: FR-CTL-12
STATEMENT: >>>
The system shall treat a dwell segment as complete only after the dwell time has elapsed *and* PV has been within a configurable tolerance band of the target (0.5–50 °C, default 5 °C) for that duration, subject to [LINK: FR-CTL-11].
<<<
PRIORITY: M
VERIFICATION: T

[REQUIREMENT]
UID: FR-CTL-13
STATEMENT: >>>
The system shall never command heating during a cooling segment; a segment whose target is below the current temperature shall be executed as a passive cooling ramp with the setpoint tracked only as an upper bound.
<<<
PRIORITY: M
VERIFICATION: T

[REQUIREMENT]
UID: FR-CTL-14
STATEMENT: >>>
The system shall support a manual mode in which the PID holds a single operator-supplied target temperature.
<<<
PRIORITY: M
VERIFICATION: T

[REQUIREMENT]
UID: FR-CTL-15
STATEMENT: >>>
The system shall expose PID internals (P, I, D contributions, error, duty, saturation flag) for diagnostics and logging.
<<<
PRIORITY: S
VERIFICATION: T

[REQUIREMENT]
UID: FR-CTL-16
STATEMENT: >>>
The system shall limit the commanded duty to a configurable maximum of 10–100 % (default 100 %), to allow derating an over-powered kiln.
<<<
PRIORITY: C
VERIFICATION: T

[[/SECTION]]

[[SECTION]]
UID: SECT-3-3
TITLE: 3.3 Automatic PID tuning (FR-TUN)

[REQUIREMENT]
UID: FR-TUN-01
STATEMENT: >>>
The system shall provide an automatic PID tuning procedure that determines Kp, Ki and Kd without operator calculation.
<<<
PRIORITY: M
VERIFICATION: T

[REQUIREMENT]
UID: FR-TUN-02
STATEMENT: >>>
Tuning shall use the **relay (Åström–Hägglund) method** [R5]: the controller drives a bounded on/off limit cycle about a tuning setpoint and measures the ultimate gain *Ku* and ultimate period *Tu* from the resulting oscillation.
<<<
PRIORITY: M
VERIFICATION: T

[REQUIREMENT]
UID: FR-TUN-03
STATEMENT: >>>
The operator shall specify the tuning setpoint; the system shall reject a setpoint above the configured maximum temperature or below ambient + 50 °C.
<<<
PRIORITY: M
VERIFICATION: T

[REQUIREMENT]
UID: FR-TUN-04
STATEMENT: >>>
The relay output shall be bounded by a configurable output amplitude *d* (10–100 % duty, default 50 %) and a configurable hysteresis (0.1–20 °C, default 1 °C).
<<<
PRIORITY: M
VERIFICATION: T

[REQUIREMENT]
UID: FR-TUN-05
STATEMENT: >>>
The system shall discard the first oscillation cycle and shall require at least **3** further cycles whose successive periods agree within 15 % and whose amplitudes agree within 20 % before accepting a result.
<<<
PRIORITY: M
VERIFICATION: T

[REQUIREMENT]
UID: FR-TUN-06
STATEMENT: >>>
The system shall derive gains using selectable rules, **Ziegler–Nichols** (classic, aggressive) and **Tyreus–Luyben** (conservative, default), and shall present both candidate gain sets to the operator.
<<<
PRIORITY: M
VERIFICATION: T

[REQUIREMENT]
UID: FR-TUN-07
STATEMENT: >>>
The system shall abort tuning and enter Fault if any safety requirement in §5 ([LINK: SECT-5]) trips, if no valid oscillation is identified within a configurable timeout (10–480 min, default 120 min), or if the operator cancels.
<<<
PRIORITY: M
VERIFICATION: T

[REQUIREMENT]
UID: FR-TUN-08
STATEMENT: >>>
Aborted tuning shall leave the previously stored gains unchanged.
<<<
PRIORITY: M
VERIFICATION: T

[REQUIREMENT]
UID: FR-TUN-09
STATEMENT: >>>
The system shall not store tuning results automatically; the operator shall explicitly accept a result before it replaces the active gains.
<<<
PRIORITY: M
VERIFICATION: D

[REQUIREMENT]
UID: FR-TUN-10
STATEMENT: >>>
The system shall report live tuning progress (phase, cycles captured, measured Ku/Tu, elapsed time) and shall record the tuning oscillation in the data log like any other run.
<<<
PRIORITY: M
VERIFICATION: T

[REQUIREMENT]
UID: FR-TUN-11
STATEMENT: >>>
The system shall store the provenance of the active gains: manual, or tuned (with rule, Ku, Tu, tuning setpoint and timestamp).
<<<
PRIORITY: S
VERIFICATION: T

[REQUIREMENT]
UID: FR-TUN-12
STATEMENT: >>>
The system shall warn the operator that the kiln must be loaded representatively and the lid closed before tuning, because the identified model includes the load.
<<<
PRIORITY: S
VERIFICATION: I

[REQUIREMENT]
UID: FR-TUN-13
STATEMENT: >>>
The system shall support storing up to **4** named gain sets (e.g. per firing range) and selecting one per program.
<<<
PRIORITY: C
VERIFICATION: T

[[/SECTION]]

[[SECTION]]
UID: SECT-3-4
TITLE: 3.4 Firing programs (FR-PRG)

[REQUIREMENT]
UID: FR-PRG-01
STATEMENT: >>>
A firing program shall consist of a name, an optional description, and an ordered list of **1–32 segments**.
<<<
PRIORITY: M
VERIFICATION: T

[REQUIREMENT]
UID: FR-PRG-02
STATEMENT: >>>
Each segment shall comprise: target temperature (0–1350 °C), ramp rate (0–9999 °C/h, 0 = maximum), and dwell time (0–5999 min).
<<<
PRIORITY: M
VERIFICATION: T

[REQUIREMENT]
UID: FR-PRG-03
STATEMENT: >>>
Each segment shall optionally carry a flag requiring **operator acknowledgement** before the program advances past it (e.g. to crack the lid for venting).
<<<
PRIORITY: S
VERIFICATION: T

[REQUIREMENT]
UID: FR-PRG-04
STATEMENT: >>>
The system shall store at least **20** programs in non-volatile storage, persisting across power loss and firmware update.
<<<
PRIORITY: M
VERIFICATION: T

[REQUIREMENT]
UID: FR-PRG-05
STATEMENT: >>>
The system shall validate a program on save and on start, rejecting it with a specific reason if: no segments; any target above the configured maximum temperature; any field out of range; total predicted duration above 168 h.
<<<
PRIORITY: M
VERIFICATION: T

[REQUIREMENT]
UID: FR-PRG-06
STATEMENT: >>>
The system shall compute and present the predicted total duration and the predicted end time of a program before it is started.
<<<
PRIORITY: M
VERIFICATION: T

[REQUIREMENT]
UID: FR-PRG-07
STATEMENT: >>>
The system shall allow creating, reading, updating, renaming, duplicating and deleting programs through the web interface.
<<<
PRIORITY: M
VERIFICATION: T

[REQUIREMENT]
UID: FR-PRG-08
STATEMENT: >>>
The system shall export and import a program as a documented, human-readable JSON file.
<<<
PRIORITY: M
VERIFICATION: T

[REQUIREMENT]
UID: FR-PRG-09
STATEMENT: >>>
The system shall ship with at least **3** example programs (e.g. bisque cone 06, glaze cone 6, glass fusing) marked read-only.
<<<
PRIORITY: S
VERIFICATION: I

[REQUIREMENT]
UID: FR-PRG-10
STATEMENT: >>>
The system shall permit editing the *remaining* segments of a running program; edits to the current or already-completed segments shall be rejected.
<<<
PRIORITY: S
VERIFICATION: T

[REQUIREMENT]
UID: FR-PRG-11
STATEMENT: >>>
The system shall record, for each run, the program content as executed, so that a later program edit does not invalidate the historical record.
<<<
PRIORITY: M
VERIFICATION: T

[[/SECTION]]

[[SECTION]]
UID: SECT-3-5
TITLE: 3.5 Run control (FR-RUN)

[REQUIREMENT]
UID: FR-RUN-01
STATEMENT: >>>
The system shall implement the state machine of §2.2 ([LINK: SECT-2-2]), and every state transition shall be logged with a timestamp and cause.
<<<
PRIORITY: M
VERIFICATION: T

[REQUIREMENT]
UID: FR-RUN-02
STATEMENT: >>>
The system shall start a program only from Idle, and only after validation ([LINK: FR-PRG-05]) and a self-check of sensor and output health has passed.
<<<
PRIORITY: M
VERIFICATION: T

[REQUIREMENT]
UID: FR-RUN-03
STATEMENT: >>>
The system shall support pause and resume; on pause, heating shall be disabled and all program timers frozen.
<<<
PRIORITY: M
VERIFICATION: T

[REQUIREMENT]
UID: FR-RUN-04
STATEMENT: >>>
The operator shall be able to abort a run at any time from the local display **and** from the web interface; abort shall de-energise heating within **1 s**.
<<<
PRIORITY: M
VERIFICATION: T

[REQUIREMENT]
UID: FR-RUN-05
STATEMENT: >>>
The system shall expose, while running: state, segment index and count, setpoint, process value, duty, rate of change, elapsed time, time remaining in segment, predicted end time, and hold-back status.
<<<
PRIORITY: M
VERIFICATION: T

[REQUIREMENT]
UID: FR-RUN-06
STATEMENT: >>>
On program completion the system shall disable heating, sound the alarm for a configurable duration (0–600 s, default 30 s), and enter Complete.
<<<
PRIORITY: M
VERIFICATION: T

[REQUIREMENT]
UID: FR-RUN-07
STATEMENT: >>>
The system shall record a **run record** for every run (program executed, gains used, start and end time, end reason, log extent, and the reference heater current established for the run, [LINK: FR-CUR-08]).
<<<
PRIORITY: M
VERIFICATION: T

[REQUIREMENT]
UID: FR-RUN-08
STATEMENT: >>>
On restart after an unexpected power loss during a run, the system shall apply the configured recovery policy: **abort** (default), or **resume** if the outage was shorter than a configurable limit (1–120 min, default 15 min) *and* PV is within a configurable band (5–200 °C, default 50 °C) of the setpoint at the time of interruption.
<<<
PRIORITY: M
VERIFICATION: T

[REQUIREMENT]
UID: FR-RUN-09
STATEMENT: >>>
The system shall persist enough run state at least every **10 s** to support [LINK: FR-RUN-08], without exceeding the flash endurance budget of [LINK: NFR-14].
<<<
PRIORITY: M
VERIFICATION: A, T

[REQUIREMENT]
UID: FR-RUN-10
STATEMENT: >>>
The system shall refuse to start a run while a fault is latched, while autotune is active, or while the enclosure temperature exceeds its limit.
<<<
PRIORITY: M
VERIFICATION: T

[[/SECTION]]

[[SECTION]]
UID: SECT-3-6
TITLE: 3.6 Local display and input (FR-HMI)

[REQUIREMENT]
UID: FR-HMI-01
STATEMENT: >>>
The system shall drive a 128×64 monochrome OLED (SSD1306/SH1106 class) over I²C.
<<<
PRIORITY: M
VERIFICATION: T

[REQUIREMENT]
UID: FR-HMI-02
STATEMENT: >>>
The default screen shall show, simultaneously and unambiguously, the **current chamber temperature** and the **target temperature**.
<<<
PRIORITY: M
VERIFICATION: D

[REQUIREMENT]
UID: FR-HMI-03
STATEMENT: >>>
The current temperature shall be rendered in the largest font on the screen, legible at 2 m.
<<<
PRIORITY: M
VERIFICATION: D

[REQUIREMENT]
UID: FR-HMI-04
STATEMENT: >>>
The default screen shall additionally show: operating state, segment index/count when running, rate of change, elapsed or remaining time, and a progress indication.
<<<
PRIORITY: M
VERIFICATION: D

[REQUIREMENT]
UID: FR-HMI-05
STATEMENT: >>>
The display shall refresh at least **twice per second**, and displayed values shall be no more than **1 s** stale.
<<<
PRIORITY: M
VERIFICATION: T

[REQUIREMENT]
UID: FR-HMI-06
STATEMENT: >>>
The system shall present a fault screen showing the fault code and a human-readable cause, which shall take precedence over all other screens and shall not be dismissible while the fault condition persists.
<<<
PRIORITY: M
VERIFICATION: T

[REQUIREMENT]
UID: FR-HMI-07
STATEMENT: >>>
The system shall display WiFi connection state and the address at which the web interface is reachable (hostname and IP).
<<<
PRIORITY: M
VERIFICATION: D

[REQUIREMENT]
UID: FR-HMI-08
STATEMENT: >>>
The system shall provide additional screens for: enclosure temperature and PID diagnostics; network details; program selection; and device information (version, uptime, gains).
<<<
PRIORITY: S
VERIFICATION: D

[REQUIREMENT]
UID: FR-HMI-09
STATEMENT: >>>
The system shall accept input from a rotary encoder with push button, distinguishing rotate, short press and long press (≥400 ms), with debouncing such that no physical detent produces more than one logical event.
<<<
PRIORITY: M
VERIFICATION: T

[REQUIREMENT]
UID: FR-HMI-10
STATEMENT: >>>
The operator shall be able to, from the local input alone: select and start a stored program, pause/resume, abort a run, acknowledge a fault, and read the WiFi address.
<<<
PRIORITY: M
VERIFICATION: D

[REQUIREMENT]
UID: FR-HMI-11
STATEMENT: >>>
Starting a program and aborting a run from the local input shall require a confirmation step.
<<<
PRIORITY: M
VERIFICATION: D

[REQUIREMENT]
UID: FR-HMI-12
STATEMENT: >>>
The system shall support a configurable display dim/blank timeout (0 = never, 10–3600 s) which shall be suspended while a fault is active.
<<<
PRIORITY: C
VERIFICATION: T

[REQUIREMENT]
UID: FR-HMI-15
STATEMENT: >>>
The local display shall render operator text in the language of `hmi.language` ([LINK: NFR-23]). Short labels shall fit the display in every language provided; a translation that does not fit is a defect in the translation, not a reason to truncate at runtime.
<<<
PRIORITY: M
VERIFICATION: T

[REQUIREMENT]
UID: FR-HMI-13
STATEMENT: >>>
Temperature shall be displayed in °C or °F according to configuration; all internal computation, storage and API values shall remain in °C.
<<<
PRIORITY: S
VERIFICATION: T

[REQUIREMENT]
UID: FR-HMI-14
STATEMENT: >>>
If the display fails to initialise or stops acknowledging on I²C, the system shall log the fault and continue controlling the kiln.
<<<
PRIORITY: M
VERIFICATION: T

[[/SECTION]]

[[SECTION]]
UID: SECT-3-7
TITLE: 3.7 Web interface (FR-WEB)

[REQUIREMENT]
UID: FR-WEB-01
STATEMENT: >>>
The system shall serve a web interface from an HTTP server on the device itself.
<<<
PRIORITY: M
VERIFICATION: T

[REQUIREMENT]
UID: FR-WEB-02
STATEMENT: >>>
All web assets shall be served from the device with **no runtime dependency on any external host** (no CDN, no external fonts, no telemetry).
<<<
PRIORITY: M
VERIFICATION: I, T

[REQUIREMENT]
UID: FR-WEB-03
STATEMENT: >>>
The interface shall be usable on a 360 px-wide phone screen and on a desktop browser, without horizontal scrolling of the page body.
<<<
PRIORITY: M
VERIFICATION: D

[REQUIREMENT]
UID: FR-WEB-04
STATEMENT: >>>
The interface shall present a live dashboard: state, current temperature, target temperature, duty, rate of change, segment progress, elapsed and remaining time, and active warnings.
<<<
PRIORITY: M
VERIFICATION: D

[REQUIREMENT]
UID: FR-WEB-05
STATEMENT: >>>
Live values shall update at least once per second without a page reload, via a push mechanism (Server-Sent Events or WebSocket) rather than polling.
<<<
PRIORITY: M
VERIFICATION: T

[REQUIREMENT]
UID: FR-WEB-06
STATEMENT: >>>
The interface shall plot **logged temperature data** as a time series chart showing at minimum the measured chamber temperature and the setpoint on a common time axis.
<<<
PRIORITY: M
VERIFICATION: D

[REQUIREMENT]
UID: FR-WEB-07
STATEMENT: >>>
The chart shall additionally offer heating duty, heater current and enclosure temperature as toggleable series, on a secondary axis where units differ.
<<<
PRIORITY: S
VERIFICATION: D

[REQUIREMENT]
UID: FR-WEB-08
STATEMENT: >>>
For a run in progress, the chart shall show the trace so far together with the **planned remainder** of the curve, so that actual and intended firing can be compared at a glance.
<<<
PRIORITY: M
VERIFICATION: D

[REQUIREMENT]
UID: FR-WEB-09
STATEMENT: >>>
The interface shall list completed runs and shall plot the logged data of any selected past run.
<<<
PRIORITY: M
VERIFICATION: D

[REQUIREMENT]
UID: FR-WEB-10
STATEMENT: >>>
The chart shall support zoom and pan over the time axis and shall read out the values at the cursor position.
<<<
PRIORITY: S
VERIFICATION: D

[REQUIREMENT]
UID: FR-WEB-11
STATEMENT: >>>
The interface shall render a chart of a **24 h run at 10 s resolution (≈8600 points)** within 2 s on a mid-range phone, decimating server-side as needed.
<<<
PRIORITY: M
VERIFICATION: T

[REQUIREMENT]
UID: FR-WEB-12
STATEMENT: >>>
The interface shall **display** a stored program as a graph and a segment table, and shall not edit one. Authoring is a local function ([LINK: FR-WEB-26]); until a local editor exists, programs are the seeded examples of [LINK: FR-PRG-09]. See [LINK: OQ-09].
<<<
PRIORITY: M
VERIFICATION: T

[REQUIREMENT]
UID: FR-WEB-13
STATEMENT: >>>
~~Client-side validation with server re-validation on save.~~ **Withdrawn 2026-10-06**: there is no save. Program validation remains in `kiln_core/profile` and runs wherever a program is stored.
<<<
PRIORITY: M
VERIFICATION: I
STATUS: Withdrawn

[REQUIREMENT]
UID: FR-WEB-14
STATEMENT: >>>
The interface shall **not** provide any means of starting, pausing, resuming or aborting a run. Run control is available only at the kiln ([LINK: FR-WEB-26]). Run *state* shall remain fully readable.
<<<
PRIORITY: M
VERIFICATION: T

[REQUIREMENT]
UID: FR-WEB-15
STATEMENT: >>>
The interface shall **not** provide manual heating, nor adjustment of the remaining segments of a running program. Both are available only at the kiln ([LINK: FR-WEB-26]).
<<<
PRIORITY: M
VERIFICATION: T

[REQUIREMENT]
UID: FR-WEB-16
STATEMENT: >>>
The interface shall allow **monitoring** an automatic PID tuning run. It shall not start, cancel or accept one: a tuning run drives the kiln through relay oscillation and is a firing by another name ([LINK: FR-WEB-26]).
<<<
PRIORITY: M
VERIFICATION: T

[REQUIREMENT]
UID: FR-WEB-17
STATEMENT: >>>
The interface shall **display** all configuration items of [LINK: FR-CFG-01] with their units, ranges and defaults, and shall not write any of them. The configured maximum temperature and the safety thresholds live here ([LINK: FR-WEB-26]).
<<<
PRIORITY: M
VERIFICATION: T

[REQUIREMENT]
UID: FR-WEB-18
STATEMENT: >>>
The interface shall allow downloading a run's log as **CSV** and as **JSON**.
<<<
PRIORITY: M
VERIFICATION: T

[REQUIREMENT]
UID: FR-WEB-19
STATEMENT: >>>
The system shall expose a documented JSON/REST API; the web UI shall use only that API, adding no privileged back channel.
<<<
PRIORITY: M
VERIFICATION: I, T

[REQUIREMENT]
UID: FR-WEB-20
STATEMENT: >>>
The API shall return errors as a JSON object with a machine-readable code and a human-readable message, using conventional HTTP status codes.
<<<
PRIORITY: M
VERIFICATION: T

[REQUIREMENT]
UID: FR-WEB-21
STATEMENT: >>>
The system shall serve at least **4** concurrent HTTP clients without the control loop missing a period ([LINK: NFR-02]).
<<<
PRIORITY: M
VERIFICATION: T

[REQUIREMENT]
UID: FR-WEB-22
STATEMENT: >>>
Web assets shall be pre-compressed and served with `Content-Encoding: gzip`, and static assets shall carry cache headers keyed to the firmware version.
<<<
PRIORITY: S
VERIFICATION: T

[REQUIREMENT]
UID: FR-WEB-23
STATEMENT: >>>
~~Optional password protection of state-changing endpoints.~~ **Withdrawn 2026-10-06.** With the interface read-only there is no state-changing endpoint to protect, and the password could not be set from anywhere in any case: [LINK: FR-WEB-26] had removed configuration writes and the local interface has no text entry. An authentication gate that can never be armed is worse than none, because it reads as protection.
<<<
PRIORITY: M
VERIFICATION: I
STATUS: Withdrawn

[REQUIREMENT]
UID: FR-WEB-24
STATEMENT: >>>
The interface shall display a clear, persistent banner whenever a fault is latched or a warning is active.
<<<
PRIORITY: M
VERIFICATION: D

[REQUIREMENT]
UID: FR-WEB-26
STATEMENT: >>>
**The web interface shall be read-only.** No endpoint reachable over the network shall change any device state: not the run, not manual heating, not tuning, not configuration, not a latched fault, not the current-transformer calibration, and not the stored programs. Every request other than `GET` shall return `403` with the code `read_only` and shall name where the control actually is. Everything the interface can do, it can do by reading.
<<<
PRIORITY: M
VERIFICATION: T

[REQUIREMENT]
UID: FR-WEB-25
STATEMENT: >>>
The interface shall remain functional with a lost connection, showing stale-data and reconnection state rather than silently displaying old values as current.
<<<
PRIORITY: S
VERIFICATION: T

[REQUIREMENT]
UID: FR-WEB-27
STATEMENT: >>>
The interface shall be operable in light and dark colour schemes following the browser preference.
<<<
PRIORITY: C
VERIFICATION: D

[[/SECTION]]

[[SECTION]]
UID: SECT-3-8
TITLE: 3.8 Data logging (FR-LOG)

[REQUIREMENT]
UID: FR-LOG-01
STATEMENT: >>>
The system shall log a temperature sample record during every run and during autotune.
<<<
PRIORITY: M
VERIFICATION: T

[REQUIREMENT]
UID: FR-LOG-02
STATEMENT: >>>
A sample record shall contain at minimum: timestamp, chamber temperature (raw and filtered), setpoint, heating duty, **heater current**, enclosure temperature, segment index, state, and a flags field.
<<<
PRIORITY: M
VERIFICATION: T

[REQUIREMENT]
UID: FR-LOG-03
STATEMENT: >>>
The sample interval shall be configurable from **1 s to 300 s**, default **10 s**.
<<<
PRIORITY: M
VERIFICATION: T

[REQUIREMENT]
UID: FR-LOG-04
STATEMENT: >>>
The system shall additionally log an out-of-band record on every state transition, fault, warning, configuration change and operator action.
<<<
PRIORITY: M
VERIFICATION: T

[REQUIREMENT]
UID: FR-LOG-05
STATEMENT: >>>
Logs shall be stored **on the device's internal flash**. The system shall not require an SD card and shall not require any external database or network service ([LINK: CON-03]).
<<<
PRIORITY: M
VERIFICATION: I, T

[REQUIREMENT]
UID: FR-LOG-06
STATEMENT: >>>
Sample logs shall be stored in a fixed-size **circular** store; when full, the oldest data shall be overwritten, and the system shall never fail a run because the log is full.
<<<
PRIORITY: M
VERIFICATION: T

[REQUIREMENT]
UID: FR-LOG-07
STATEMENT: >>>
The log store shall retain at least **150 h** of samples at the default 10 s interval.
<<<
PRIORITY: M
VERIFICATION: A, T

[REQUIREMENT]
UID: FR-LOG-08
STATEMENT: >>>
The log store shall be append-structured so that a power loss can corrupt at most the record being written, and the reader shall detect and skip a torn record.
<<<
PRIORITY: M
VERIFICATION: T

[REQUIREMENT]
UID: FR-LOG-09
STATEMENT: >>>
The system shall retain the run records ([LINK: FR-RUN-07]) of at least the **20** most recent runs, including those whose samples have been overwritten, and shall mark such runs as having truncated data.
<<<
PRIORITY: M
VERIFICATION: T

[REQUIREMENT]
UID: FR-LOG-10
STATEMENT: >>>
The system shall expose logged data through the API with selection by run and time range, and with server-side decimation to a caller-specified maximum point count.
<<<
PRIORITY: M
VERIFICATION: T

[REQUIREMENT]
UID: FR-LOG-11
STATEMENT: >>>
Decimation shall preserve visible extrema (min/max per bucket), so that a short temperature excursion is not hidden by downsampling.
<<<
PRIORITY: M
VERIFICATION: T

[REQUIREMENT]
UID: FR-LOG-12
STATEMENT: >>>
Every record shall carry a monotonic device timestamp; where wall-clock time is known ([LINK: FR-NET-06]) records shall additionally carry UTC, and records logged before time sync shall be marked as such.
<<<
PRIORITY: M
VERIFICATION: T

[REQUIREMENT]
UID: FR-LOG-13
STATEMENT: >>>
The operator shall be able to erase all logs, and shall be warned that the action is irreversible.
<<<
PRIORITY: S
VERIFICATION: T

[REQUIREMENT]
UID: FR-LOG-14
STATEMENT: >>>
Logging shall never block the control loop; if the log store is unavailable the system shall continue controlling and raise a warning.
<<<
PRIORITY: M
VERIFICATION: T

[REQUIREMENT]
UID: FR-LOG-15
STATEMENT: >>>
The system shall report log store health: used and free capacity, oldest and newest record time, and write error count.
<<<
PRIORITY: S
VERIFICATION: T

[[/SECTION]]

[[SECTION]]
UID: SECT-3-9
TITLE: 3.9 Configuration (FR-CFG)

[REQUIREMENT]
UID: FR-CFG-01
STATEMENT: >>>
The system shall hold all tunable parameters in a single versioned configuration structure in non-volatile storage, each item having a type, unit, range and default.
<<<
PRIORITY: M
VERIFICATION: T

[REQUIREMENT]
UID: FR-CFG-02
STATEMENT: >>>
The configuration shall include at minimum: **safety**: maximum chamber temperature, maximum enclosure temperature, runaway detection parameters, power-loss recovery policy; **control**: Kp, Ki, Kd, loop period, PWM window, minimum on/off time, maximum duty, hold-back band, dwell tolerance; **sensing**: TC types, line filter frequency, filter time constant, calibration offset and gain for both channels; **tuning**: amplitude, hysteresis, rule, timeout; **current**: CT ratio and output type, nominal heater current, mains voltage, fail-on and fail-off thresholds and settle times, deviation bands, over-current limit, relay life limits, monitoring enable; **logging**: sample interval; **HMI**: units, dim timeout, alarm duration; **network**: WiFi mode and credentials, hostname, AP SSID and passphrase, NTP server, timezone; **security**: none, since [LINK: FR-WEB-26] left nothing reachable over the network to authenticate.
<<<
PRIORITY: M
VERIFICATION: I

[REQUIREMENT]
UID: FR-CFG-03
STATEMENT: >>>
The system shall validate every configuration write against its declared range and shall reject the whole write atomically if any item is invalid.
<<<
PRIORITY: M
VERIFICATION: T

[REQUIREMENT]
UID: FR-CFG-04
STATEMENT: >>>
The system shall apply a configuration change without a reboot wherever physically possible, and shall clearly mark items that require a reboot.
<<<
PRIORITY: S
VERIFICATION: T

[REQUIREMENT]
UID: FR-CFG-05
STATEMENT: >>>
On reading a configuration written by an older firmware version, the system shall migrate it, filling new items with defaults; on reading an unreadable or corrupt configuration it shall fall back to defaults and raise a warning.
<<<
PRIORITY: M
VERIFICATION: T

[REQUIREMENT]
UID: FR-CFG-06
STATEMENT: >>>
The system shall support restoring all configuration to defaults, and shall support exporting and importing configuration as JSON (excluding secrets).
<<<
PRIORITY: S
VERIFICATION: T

[REQUIREMENT]
UID: FR-CFG-07
STATEMENT: >>>
The system shall never return stored passwords or passphrases through the API; it shall return only whether a secret is set.
<<<
PRIORITY: M
VERIFICATION: T

[REQUIREMENT]
UID: FR-CFG-08
STATEMENT: >>>
The system shall reject changes to safety-relevant configuration while a run is in progress.
<<<
PRIORITY: M
VERIFICATION: T

[[/SECTION]]

[[SECTION]]
UID: SECT-3-10
TITLE: 3.10 Connectivity and time (FR-NET)

[REQUIREMENT]
UID: FR-NET-01
STATEMENT: >>>
The system shall connect to a WiFi network as a station using stored credentials.
<<<
PRIORITY: M
VERIFICATION: T

[REQUIREMENT]
UID: FR-NET-02
STATEMENT: >>>
If no credentials are stored, or if the station connection fails for a configurable period (30–600 s, default 60 s), the system shall start its own access point and serve a provisioning page on it.
<<<
PRIORITY: M
VERIFICATION: T

[REQUIREMENT]
UID: FR-NET-03
STATEMENT: >>>
The system shall retry the station connection with exponential backoff indefinitely, without interfering with control or safety functions.
<<<
PRIORITY: M
VERIFICATION: T

[REQUIREMENT]
UID: FR-NET-04
STATEMENT: >>>
The system shall advertise itself over mDNS under a configurable hostname (default `kiln`), so the interface is reachable as `kiln.local`.
<<<
PRIORITY: M
VERIFICATION: T

[REQUIREMENT]
UID: FR-NET-05
STATEMENT: >>>
The AP fallback shall require a passphrase of at least 8 characters, with a device-unique default derived from the MAC address and shown on the local display.
<<<
PRIORITY: M
VERIFICATION: T

[REQUIREMENT]
UID: FR-NET-06
STATEMENT: >>>
The system shall synchronise wall-clock time by SNTP when a route to the internet exists, and shall apply a configurable timezone with daylight-saving rules.
<<<
PRIORITY: M
VERIFICATION: T

[REQUIREMENT]
UID: FR-NET-07
STATEMENT: >>>
Loss of WiFi, of the internet, or of time sync shall not interrupt, pause or otherwise alter a running firing.
<<<
PRIORITY: M
VERIFICATION: T

[REQUIREMENT]
UID: FR-NET-08
STATEMENT: >>>
The system shall maintain a monotonic time base for all control, safety and log timing that is unaffected by wall-clock adjustments.
<<<
PRIORITY: M
VERIFICATION: T

[REQUIREMENT]
UID: FR-NET-09
STATEMENT: >>>
The system shall expose WiFi diagnostics: mode, SSID, IP, RSSI, uptime, disconnect count, and last disconnect reason.
<<<
PRIORITY: S
VERIFICATION: T

[REQUIREMENT]
UID: FR-NET-10
STATEMENT: >>>
The system shall support optional remote logging of events to a syslog server over UDP.
<<<
PRIORITY: C
VERIFICATION: T

[[/SECTION]]

[[SECTION]]
UID: SECT-3-11
TITLE: 3.11 Firmware update (FR-UPD)

[REQUIREMENT]
UID: FR-UPD-01
STATEMENT: >>>
The system shall **not** accept a firmware image over the network ([LINK: FR-WEB-26]): an update path is total and persistent control of the heater, and the web interface is an observation surface. A local update path (USB/serial, or an update initiated at the kiln) shall be specified before release, see [LINK: OQ-08]. Until then the device has **no field update path**, which is a known and accepted gap.
<<<
PRIORITY: M
VERIFICATION: I

[REQUIREMENT]
UID: FR-UPD-02
STATEMENT: >>>
The system shall use dual OTA application partitions and shall fall back to the previous firmware if the new image fails to confirm itself as bootable.
<<<
PRIORITY: M
VERIFICATION: T

[REQUIREMENT]
UID: FR-UPD-03
STATEMENT: >>>
The system shall verify the integrity of an uploaded image before marking it bootable, and shall reject an image that is not a valid application for this target.
<<<
PRIORITY: M
VERIFICATION: T

[REQUIREMENT]
UID: FR-UPD-04
STATEMENT: >>>
The system shall refuse a firmware update while a run or autotune is in progress.
<<<
PRIORITY: M
VERIFICATION: T

[REQUIREMENT]
UID: FR-UPD-05
STATEMENT: >>>
A firmware update shall preserve configuration, stored programs and run records; loss of sample log data across an update is acceptable if the log partition layout changes, and shall be stated in release notes.
<<<
PRIORITY: M
VERIFICATION: T

[REQUIREMENT]
UID: FR-UPD-06
STATEMENT: >>>
The system shall report the running firmware version, build time, git revision and target in the interface and via the API. The version shall follow **semantic versioning** and shall be derived by the build from the release tag rather than maintained by hand, so that it cannot disagree with the tag it was built from. A build that is not on a release tag shall remain a valid semantic version and shall say so, by carrying the commit count and revision as build metadata.
<<<
PRIORITY: M
VERIFICATION: T

[REQUIREMENT]
UID: FR-UPD-07
STATEMENT: >>>
The system shall report update progress and a clear success or failure result.
<<<
PRIORITY: S
VERIFICATION: D

[REQUIREMENT]
UID: FR-UPD-08
STATEMENT: >>>
No client, authenticated or otherwise, shall be able to initiate a firmware update over the network ([LINK: FR-UPD-01], [LINK: FR-WEB-26]).
<<<
PRIORITY: M
VERIFICATION: T

[[/SECTION]]

[[SECTION]]
UID: SECT-3-12
TITLE: 3.12 Heater current measurement (FR-CUR)

[TEXT]
STATEMENT: >>>
> Measuring the current actually flowing in the heating elements turns three
> safety detections from slow thermal *inferences* into fast electrical *facts*.
> [LINK: SR-07] needs 15 minutes of missing temperature
> rise to conclude the elements are not heating; a current measurement says so in
> one switching window.
<<<

[REQUIREMENT]
UID: FR-CUR-01
STATEMENT: >>>
The system shall measure the current in the heater circuit using a current transformer (Stromwandler) fitted around one heater conductor, downstream of both the safety contactor and the SSR, so that the measurement reflects current actually reaching the elements.
<<<
PRIORITY: M
VERIFICATION: T

[REQUIREMENT]
UID: FR-CUR-02
STATEMENT: >>>
The system shall measure true RMS current over a configurable nominal range of **0–60 A**, with a resolution of **0.1 A** and an accuracy of **±3 % of reading or ±0.3 A, whichever is greater**, after calibration.
<<<
PRIORITY: M
VERIFICATION: T

[REQUIREMENT]
UID: FR-CUR-03
STATEMENT: >>>
RMS shall be computed from samples taken at **≥ 1 kHz** over a whole number of mains cycles, so that the result is independent of sampling phase.
<<<
PRIORITY: M
VERIFICATION: T

[REQUIREMENT]
UID: FR-CUR-04
STATEMENT: >>>
Measurement shall be **gated to the commanded output state**: the system shall measure conduction current only within a commanded-on interval and leakage current only within a commanded-off interval, in each case after a configurable settle delay (0–200 ms, default 20 ms) that allows for zero-cross turn-on and CT settling.
<<<
PRIORITY: M
VERIFICATION: T

[REQUIREMENT]
UID: FR-CUR-05
STATEMENT: >>>
The system shall not attempt a conduction measurement when the commanded on-interval is shorter than the settle delay plus one full mains cycle; such windows shall be skipped rather than reported as zero current.
<<<
PRIORITY: M
VERIFICATION: T

[REQUIREMENT]
UID: FR-CUR-06
STATEMENT: >>>
The system shall apply a configurable CT ratio, a gain calibration of 0.50–2.00 and a zero offset, and shall support a one-point calibration against a known load or reference meter.
<<<
PRIORITY: M
VERIFICATION: T

[REQUIREMENT]
UID: FR-CUR-07
STATEMENT: >>>
The system shall derive and expose apparent power and cumulative energy per run from the measured current and a configured mains voltage, stating that a resistive load is assumed.
<<<
PRIORITY: S
VERIFICATION: T

[REQUIREMENT]
UID: FR-CUR-08
STATEMENT: >>>
On each run the system shall establish a **reference current**: the median conduction current measured while the elements are cold and fully on, recorded in the run record ([LINK: FR-RUN-07]) and used as the baseline for [LINK: SR-28].
<<<
PRIORITY: M
VERIFICATION: T

[REQUIREMENT]
UID: FR-CUR-09
STATEMENT: >>>
The system shall log heater current in every sample record ([LINK: FR-LOG-02]).
<<<
PRIORITY: M
VERIFICATION: T

[REQUIREMENT]
UID: FR-CUR-10
STATEMENT: >>>
The system shall present heater current live in the web interface, as a chart series, and on a local diagnostics screen.
<<<
PRIORITY: M
VERIFICATION: D

[REQUIREMENT]
UID: FR-CUR-11
STATEMENT: >>>
The system shall detect an absent, disconnected or shorted current transformer, distinguishing it from a genuine zero-current reading by the absence of any signal at all including noise floor.
<<<
PRIORITY: M
VERIFICATION: T

[REQUIREMENT]
UID: FR-CUR-12
STATEMENT: >>>
The system shall refuse to start a run when current monitoring is unavailable, **unless** current monitoring has been explicitly disabled in configuration; while it is disabled the system shall raise a persistent warning and shall rely solely on the thermal detections of [LINK: SR-07] and [LINK: SR-08].
<<<
PRIORITY: M
VERIFICATION: T

[REQUIREMENT]
UID: FR-CUR-13
STATEMENT: >>>
The system shall count and persist the number of switching operations of the contactor and of each SSR, for the wear warning of [LINK: SR-30].
<<<
PRIORITY: M
VERIFICATION: T

[REQUIREMENT]
UID: FR-CUR-14
STATEMENT: >>>
Current measurement shall not delay or block the control or safety cycles ([LINK: NFR-02]).
<<<
PRIORITY: M
VERIFICATION: T

[[/SECTION]]

[[SECTION]]
UID: SECT-3-13
TITLE: 3.13 Device identity (FR-PROD)

[TEXT]
STATEMENT: >>>
> Two kinds of identity, kept apart on purpose.
>
> The **firmware** version answers "what is running on this unit", changes with
> every release, and is derived from the release tag by the build so that no
> human has to remember to update it.
>
> The **unit** identity answers "which unit is this", is written once at
> manufacture and never again, and must survive everything the firmware is
> allowed to do to its own storage, including the configuration erase that
> [LINK: FR-CFG-05] permits on an NVS format change.
>
> A support conversation needs both, which is why they are reported together.
<<<

[REQUIREMENT]
UID: FR-PROD-01
STATEMENT: >>>
The device shall carry a **production data block** in non-volatile storage containing the manufacturer, the device model, the board revision, the serial number and the production date. It shall be held in a storage partition separate from the one holding operator configuration, so that erasing or reformatting configuration storage cannot destroy it.
<<<
PRIORITY: M
VERIFICATION: T, I

[REQUIREMENT]
UID: FR-PROD-02
STATEMENT: >>>
The firmware shall read the production data block **read-only**. No firmware function, local or remote, shall write, modify or erase it; the only writer shall be a production tool acting over a programming interface at manufacture.
<<<
PRIORITY: M
VERIFICATION: I

[REQUIREMENT]
UID: FR-PROD-03
STATEMENT: >>>
The production data block shall be reported in the device information API alongside the firmware version of [LINK: FR-UPD-06], and shown in the web interface.
<<<
PRIORITY: S
VERIFICATION: T

[REQUIREMENT]
UID: FR-PROD-04
STATEMENT: >>>
A device whose production data block is absent or incomplete shall boot and operate normally, and shall report its identity as **unprogrammed** rather than reporting partial or invented values. Incompleteness shall be treated as absence: a block missing any required field shall not be reported as programmed.
<<<
PRIORITY: M
VERIFICATION: T

[REQUIREMENT]
UID: FR-PROD-05
STATEMENT: >>>
A tool shall be provided that creates the production data block and writes it to a device, validating every field before writing, and taking the target storage offset from the firmware's own partition table rather than from a separately maintained constant.
<<<
PRIORITY: M
VERIFICATION: T, D

[[/SECTION]]

[[/SECTION]]

[[SECTION]]
UID: SECT-4
TITLE: 4. Non-functional requirements

[REQUIREMENT]
UID: NFR-01
STATEMENT: >>>
The temperature control loop shall execute at its configured period with a jitter not exceeding **±5 %** of the period, under all supported load conditions including active web clients, OTA-idle, and WiFi reconnection.
<<<
PRIORITY: M
VERIFICATION: T

[REQUIREMENT]
UID: NFR-02
STATEMENT: >>>
No non-safety activity (HTTP serving, log writing, display update, WiFi management) shall be able to delay a control or safety cycle by more than **50 ms**.
<<<
PRIORITY: M
VERIFICATION: T

[REQUIREMENT]
UID: NFR-03
STATEMENT: >>>
The safety supervisor shall evaluate its conditions at least **4 times per second**.
<<<
PRIORITY: M
VERIFICATION: T

[REQUIREMENT]
UID: NFR-04
STATEMENT: >>>
Heating shall be de-energised within **500 ms** of a safety condition being detectable, and the contactor shall open within **1 s**.
<<<
PRIORITY: M
VERIFICATION: T

[REQUIREMENT]
UID: NFR-05
STATEMENT: >>>
The system shall control temperature to within **±5 °C** of setpoint during a dwell, on a kiln whose PID has been tuned by the procedure of FR-TUN ([LINK: SECT-3-3]).
<<<
PRIORITY: M
VERIFICATION: T

[REQUIREMENT]
UID: NFR-06
STATEMENT: >>>
The system shall follow a ramp within **±15 °C** of the commanded setpoint, given a ramp rate the kiln is physically capable of.
<<<
PRIORITY: S
VERIFICATION: T

[REQUIREMENT]
UID: NFR-07
STATEMENT: >>>
Steady-state offset during dwell shall be less than **2 °C** after settling.
<<<
PRIORITY: S
VERIFICATION: T

[REQUIREMENT]
UID: NFR-08
STATEMENT: >>>
Temperature overshoot after a ramp-to-dwell transition shall not exceed **10 °C** with Tyreus–Luyben gains.
<<<
PRIORITY: S
VERIFICATION: T

[REQUIREMENT]
UID: NFR-09
STATEMENT: >>>
The firmware shall boot to a state where temperature is measured and heating is safely off within **3 s** of reset.
<<<
PRIORITY: M
VERIFICATION: T

[REQUIREMENT]
UID: NFR-10
STATEMENT: >>>
The system shall operate unattended for a **168 h** continuous run without restart, memory exhaustion, or degradation of loop timing.
<<<
PRIORITY: M
VERIFICATION: T

[REQUIREMENT]
UID: NFR-11
STATEMENT: >>>
The system shall show no net growth in free heap over a 24 h soak with an active web client, beyond a documented allocator noise band.
<<<
PRIORITY: M
VERIFICATION: T

[REQUIREMENT]
UID: NFR-12
STATEMENT: >>>
Static RAM plus peak dynamic allocation shall leave at least **48 kB** of free internal heap at all times.
<<<
PRIORITY: M
VERIFICATION: A, T

[REQUIREMENT]
UID: NFR-13
STATEMENT: >>>
The application image shall fit an OTA partition of **2 MB**; the design shall target ≤ **8 MB** total flash and shall not require PSRAM.
<<<
PRIORITY: M
VERIFICATION: A

[REQUIREMENT]
UID: NFR-14
STATEMENT: >>>
Flash write patterns shall keep every erase block below **50 000** erase cycles over a 10-year life at the default configuration, assuming 100 000-cycle endurance.
<<<
PRIORITY: M
VERIFICATION: A

[REQUIREMENT]
UID: NFR-15
STATEMENT: >>>
A watchdog reset, brownout or panic shall leave heating de-energised and shall be recorded in non-volatile storage with the reset cause.
<<<
PRIORITY: M
VERIFICATION: T

[REQUIREMENT]
UID: NFR-16
STATEMENT: >>>
The system shall recover from any unexpected reset into a defined state within [LINK: NFR-09], applying the recovery policy of [LINK: FR-RUN-08].
<<<
PRIORITY: M
VERIFICATION: T

[REQUIREMENT]
UID: NFR-17
STATEMENT: >>>
Every error path shall be handled explicitly; an unchecked failing call in control, safety or storage code shall be treated as a defect.
<<<
PRIORITY: M
VERIFICATION: A, I

[REQUIREMENT]
UID: NFR-18
STATEMENT: >>>
All source files shall carry an SPDX licence identifier of `GPL-3.0-or-later`, and the distribution shall include the full licence text and third-party notices.
<<<
PRIORITY: M
VERIFICATION: I

[REQUIREMENT]
UID: NFR-19
STATEMENT: >>>
The HTTP server shall treat every request body and parameter as untrusted: bounded lengths, no unbounded allocation, no format-string or path-traversal exposure. Authentication shall use a constant-time comparison and shall rate-limit failed attempts.
<<<
PRIORITY: M
VERIFICATION: T

[REQUIREMENT]
UID: NFR-20
STATEMENT: >>>
The device is designed for a **trusted local network**. It shall not be exposed directly to the internet, and the documentation shall state this.
<<<
PRIORITY: M
VERIFICATION: I

[REQUIREMENT]
UID: NFR-21
STATEMENT: >>>
The system shall not transmit any data to any third party.
<<<
PRIORITY: M
VERIFICATION: I

[REQUIREMENT]
UID: NFR-22
STATEMENT: >>>
The system shall have no hardcoded credentials, no default-enabled remote access other than the documented local interface, and no undocumented service ports.
<<<
PRIORITY: M
VERIFICATION: I

[REQUIREMENT]
UID: NFR-23
STATEMENT: >>>
Operator-facing text shall be held in a **single resource location**, indexed by language, with no text embedded at its point of use. **English and German** shall both be provided, selected by the `hmi.language` configuration item and offered on the local display and in the web interface. A language with no entry for a string shall fall back to English rather than showing nothing. Diagnostic output, the event log and requirement identifiers shall remain English regardless of the setting, so that a fault quoted in a report reads the same whoever filed it.
<<<
PRIORITY: M
VERIFICATION: T

[REQUIREMENT]
UID: NFR-24
STATEMENT: >>>
The system shall log internally at selectable verbosity, and production builds shall not emit debug output on the pins used by any peripheral.
<<<
PRIORITY: M
VERIFICATION: I

[REQUIREMENT]
UID: NFR-25
STATEMENT: >>>
Code shall build warning-free with `-Wall -Wextra -Werror` and shall pass the project's static analysis configuration.
<<<
PRIORITY: M
VERIFICATION: A

[REQUIREMENT]
UID: NFR-26
STATEMENT: >>>
Documentation shall cover: assembly and wiring, mains safety, commissioning, autotuning, program authoring, the REST API, the log record format, and current-transformer fitting and calibration.
<<<
PRIORITY: M
VERIFICATION: I

[REQUIREMENT]
UID: NFR-27
STATEMENT: >>>
Uncommanded heater current ([LINK: SR-25]) shall de-energise heating within **1 s** of the offending measurement window, and the weld discrimination of [LINK: SR-27] shall reach its verdict within a further **3 s**.
<<<
PRIORITY: M
VERIFICATION: T

[[/SECTION]]

[[SECTION]]
UID: SECT-5
TITLE: 5. Safety requirements

[TEXT]
STATEMENT: >>>
> A kiln is a multi-kilowatt mains-powered heater that reaches temperatures at
> which its own wiring, the enclosure and the building are at risk. The
> requirements in this section are the reason this project exists in the form it
> does, and take precedence over every functional requirement. They are all
> mandatory.
<<<

[[SECTION]]
UID: SECT-5-1
TITLE: 5.1 Safety principles

[REQUIREMENT]
UID: SR-01
STATEMENT: >>>
The system shall be **fail-safe**: any single failure of software, MCU, sensor, or SSR shall result in heating being de-energised, never in uncontrolled heating.
<<<
VERIFICATION: A, T

[REQUIREMENT]
UID: SR-02
STATEMENT: >>>
Heating shall be enabled only by the *active and continuous* assertion of software; no static condition, boot state, hung task or crashed firmware shall be capable of holding heating on.
<<<
VERIFICATION: A, T

[REQUIREMENT]
UID: SR-03
STATEMENT: >>>
The heating output stage shall consist of an SSR for modulation **in series with** an electromechanical contactor that provides an independent break, each controlled by a separate output.
<<<
VERIFICATION: I

[[/SECTION]]

[[SECTION]]
UID: SECT-5-2
TITLE: 5.2 Detection requirements

[TEXT]
STATEMENT: >>>
> **Defence in depth.** The current-based rules ([LINK: SR-25]–[LINK: SR-30])
> are the *primary* detection of a failed relay, contactor or element, because
> they are fast and unambiguous. The thermal rules ([LINK: SR-07],
> [LINK: SR-08]) are **retained unchanged** as an
> independent backstop: they use a different sensor and a different physical
> principle, so they still cover the case where the current transformer itself
> has failed or been left unfitted ([LINK: FR-CUR-12]).
> Neither may be removed on the grounds that the other exists.
<<<

[REQUIREMENT]
UID: SR-04
STATEMENT: >>>
**Thermocouple failure.** The system shall detect open circuit, short circuit, out-of-range reading, cold-junction fault, and front-end communication failure. A fault persisting beyond the grace period of [LINK: FR-ACQ-12] shall de-energise heating and latch a fault.
<<<
VERIFICATION: T

[REQUIREMENT]
UID: SR-05
STATEMENT: >>>
**Reversed thermocouple.** The system shall detect a thermocouple connected with reversed polarity, indicated by the reading falling while heating is commanded at high duty, and shall latch a fault.
<<<
VERIFICATION: T

[REQUIREMENT]
UID: SR-06
STATEMENT: >>>
**Stuck sensor.** The system shall detect a reading that does not change by more than a configurable threshold (default 2 °C) while heating is commanded above a configurable duty (default 50 %) for a configurable period (default 10 min), and shall latch a fault.
<<<
VERIFICATION: T

[REQUIREMENT]
UID: SR-07
STATEMENT: >>>
**Thermal runaway / heating failure.** The system shall latch a fault if heating is commanded above a configurable duty (default 80 %) for longer than a configurable period (default 15 min) while the measured rate of rise remains below a configurable threshold (default 10 °C/h). This covers a failed element, an open contactor, an open safety chain and an open kiln lid.
<<<
VERIFICATION: T

[REQUIREMENT]
UID: SR-08
STATEMENT: >>>
**Shorted SSR / uncommanded heating.** The system shall latch a fault, open the contactor and alarm if the temperature rises by more than a configurable threshold (default 5 °C) over a configurable period (default 3 min) while commanded duty is zero.
<<<
VERIFICATION: T

[REQUIREMENT]
UID: SR-09
STATEMENT: >>>
**Over-temperature.** The system shall de-energise heating whenever the chamber temperature exceeds the configured maximum chamber temperature, and shall latch a fault if it exceeds it by a configurable margin (default 10 °C).
<<<
VERIFICATION: T

[REQUIREMENT]
UID: SR-10
STATEMENT: >>>
**Setpoint excursion.** The system shall latch a fault if PV exceeds SP by more than a configurable band (default 50 °C) for longer than a configurable period (default 2 min).
<<<
VERIFICATION: T

[REQUIREMENT]
UID: SR-11
STATEMENT: >>>
**Enclosure over-temperature.** The system shall latch a fault if the enclosure/electronics temperature exceeds the configured maximum (default 70 °C), protecting the controller and its wiring.
<<<
VERIFICATION: T

[REQUIREMENT]
UID: SR-12
STATEMENT: >>>
**Insulation degradation.** The system shall record, per firing, the heating energy (duty × time) required to reach reference temperatures, and shall raise a warning when it exceeds the established baseline by a configurable factor (default 1.3), indicating failing insulation or ageing elements.
<<<
VERIFICATION: T

[REQUIREMENT]
UID: SR-13
STATEMENT: >>>
**Loss of control.** The system shall latch a fault if the control loop fails to complete a cycle within twice its configured period, or if the safety supervisor fails to run within its deadline.
<<<
VERIFICATION: T

[REQUIREMENT]
UID: SR-14
STATEMENT: >>>
**Watchdog.** The system shall enable the hardware watchdog and a per-task watchdog covering the control and safety tasks; a watchdog expiry shall de-energise heating through the mechanism of [LINK: SR-02] and reset the device.
<<<
VERIFICATION: T

[REQUIREMENT]
UID: SR-15
STATEMENT: >>>
**Brownout.** The system shall enable brownout detection, and a brownout reset shall leave heating de-energised.
<<<
VERIFICATION: T

[REQUIREMENT]
UID: SR-25
STATEMENT: >>>
**Relay fail-on (uncommanded current).** The system shall latch a fault when measured heater current exceeds a configurable threshold (default 0.5 A) during a commanded-off interval, after the settle delay of [LINK: FR-CUR-04], for a configurable number of consecutive measurement windows (default 2). This is the direct electrical counterpart of [LINK: SR-08] and shall act on it rather than waiting for a temperature rise.
<<<
VERIFICATION: T

[REQUIREMENT]
UID: SR-26
STATEMENT: >>>
**Relay or element fail-off (no current when commanded).** The system shall latch a fault when measured conduction current remains below a configurable threshold (default 20 % of the reference current) during commanded-on intervals for a configurable period (default 30 s). This covers a failed SSR, an open contactor, an open safety chain, a blown heater fuse and fully open elements, and shall act long before the thermal detection of [LINK: SR-07].
<<<
VERIFICATION: T

[REQUIREMENT]
UID: SR-27
STATEMENT: >>>
**Weld discrimination.** On detecting uncommanded current ([LINK: SR-25]) the system shall de-assert heat enable so the contactor opens, wait a configurable interval (contactor drop-out time plus margin, default 2 s), and re-measure. If current has ceased it shall latch **SSR shorted**; if current persists it shall latch **contactor welded**, which is the more severe fault and whose operator instruction shall be to isolate the kiln at its supply, because the controller has no remaining means of interrupting the current.
<<<
VERIFICATION: T

[REQUIREMENT]
UID: SR-28
STATEMENT: >>>
**Partial element failure / current deviation.** The system shall compare conduction current against the reference current of [LINK: FR-CUR-08], corrected for the known positive temperature coefficient of the elements where configured, and shall raise a warning at a configurable deviation (default 10 %) and latch a fault at a configurable deviation (default 25 %). Losing one of several element groups is a step change of a known fraction and shall be detected as such.
<<<
VERIFICATION: T

[REQUIREMENT]
UID: SR-29
STATEMENT: >>>
**Over-current.** The system shall latch a fault when measured current exceeds a configurable maximum (default 120 % of nominal), indicating a shorted element, incorrect wiring or a failed SSR passing excessive current.
<<<
VERIFICATION: T

[REQUIREMENT]
UID: SR-30
STATEMENT: >>>
**Relay wear / incipient failure.** The system shall raise a warning when the switching-operation count of the contactor or an SSR reaches a configurable life limit, and shall additionally raise a warning when current mismatches of the kind described in [LINK: SR-25] or [LINK: SR-26] occur intermittently and self-clear, an early indication that a relay is becoming defective before it fails outright.
<<<
VERIFICATION: T

[REQUIREMENT]
UID: SR-31
STATEMENT: >>>
**Door / lid interlock.** Where a door interlock switch is fitted, the system shall de-energise heating and open the contactor **immediately**: within one safety cycle, with no confirmation delay, whenever the switch indicates the door is open, and shall latch a fault if it remains open for a configurable confirmation period (0–0.5 s, default 0.2 s) while a heating state is active. The switch shall be **normally closed**, so that an open circuit, a disconnected plug or a failed switch all read as "door open". Where no interlock is fitted the rule shall stand down and a warning shall be raised; it shall not be possible for an unread input to be interpreted as a closed door.
<<<
VERIFICATION: T

[[/SECTION]]

[[SECTION]]
UID: SECT-5-3
TITLE: 5.3 Reaction and recovery requirements

[REQUIREMENT]
UID: SR-16
STATEMENT: >>>
On any fault the system shall, in this order: command zero duty, de-assert heat enable so the contactor opens, assert the alarm output, latch the fault with its code and a snapshot of relevant values, log it, and enter Fault state.
<<<
VERIFICATION: T

[REQUIREMENT]
UID: SR-17
STATEMENT: >>>
A latched fault shall persist across power loss, and shall require an explicit operator acknowledgement to clear. The system shall not silently self-recover.
<<<
VERIFICATION: T

[REQUIREMENT]
UID: SR-18
STATEMENT: >>>
The system shall refuse to clear a fault while its triggering condition is still present.
<<<
VERIFICATION: T

[REQUIREMENT]
UID: SR-19
STATEMENT: >>>
Each fault shall have a unique, stable numeric code and a human-readable cause, presented on both the display and the web interface, and documented.
<<<
VERIFICATION: I, T

[REQUIREMENT]
UID: SR-20
STATEMENT: >>>
The on-board buzzer ([LINK: HR-09]) shall sound on any fault and on program completion, and the two shall be audibly distinguishable by their pattern.
<<<
VERIFICATION: D

[REQUIREMENT]
UID: SR-21
STATEMENT: >>>
Heating outputs shall be de-energised during reset, boot, firmware update and any transition through an undefined software state.
<<<
VERIFICATION: I, T

[REQUIREMENT]
UID: SR-22
STATEMENT: >>>
Every safety detection threshold shall be configurable within a bounded range, and no range shall permit disabling a detection entirely except where explicitly stated ([LINK: SR-12] warning only).
<<<
VERIFICATION: I, T

[REQUIREMENT]
UID: SR-23
STATEMENT: >>>
The maximum chamber temperature shall be configurable only up to an absolute compile-time ceiling of **1300 °C**, and every temperature setpoint, program target and tuning setpoint shall be clamped to the configured maximum.

The independent safety supervisor's hard-coded backstop shall be **1350 °C**, above this ceiling, so that the configurable limit is always reachable and the backstop is always beyond it. The two values shall be stated together wherever either appears; limits that can be edited apart eventually cross. The 1300 °C ceiling is above cone 10 (about 1285 °C), and 1350 °C is the top of type K's usable range ([LINK: FR-ACQ-05]), which is why the ceiling moved down rather than the backstop up.
<<<
VERIFICATION: T

[REQUIREMENT]
UID: SR-24
STATEMENT: >>>
The documentation shall state that Safe Kiln Controller is **not** a safety-certified device, that an independent hardware over-temperature cutout is required ([LINK: HR-13]), and that mains wiring must be performed by a competent person in accordance with local regulation [R6].
<<<
VERIFICATION: I

[[/SECTION]]

[[/SECTION]]

[[SECTION]]
UID: SECT-6
TITLE: 6. Hardware interface requirements

[TEXT]
STATEMENT: >>>
> This section constrains the firmware's view of the hardware. The board design
> itself is documented in `hardware/`.
<<<

[REQUIREMENT]
UID: HR-01
STATEMENT: >>>
The controller shall be an **ESP32-S3** with at least 8 MB flash; PSRAM shall not be required.
<<<
PRIORITY: M
VERIFICATION: I

[REQUIREMENT]
UID: HR-02
STATEMENT: >>>
The chamber and enclosure thermocouple front-ends shall be MAX31856 devices on a shared SPI bus with individual chip selects.
<<<
PRIORITY: M
VERIFICATION: I

[REQUIREMENT]
UID: HR-03
STATEMENT: >>>
The thermocouple front-end SPI bus shall be separate from, or arbitrated independently of, any bus shared with a peripheral that can stall it.
<<<
PRIORITY: M
VERIFICATION: I

[REQUIREMENT]
UID: HR-04
STATEMENT: >>>
The display shall be a 128×64 monochrome OLED on I²C, at a configurable address (default 0x3C).
<<<
PRIORITY: M
VERIFICATION: I

[REQUIREMENT]
UID: HR-05
STATEMENT: >>>
The operator input shall be a quadrature rotary encoder with a push button, read by hardware (pulse counter unit) rather than by polling in software.
<<<
PRIORITY: M
VERIFICATION: I

[REQUIREMENT]
UID: HR-06
STATEMENT: >>>
The heater modulation output shall drive a zero-cross-switching SSR rated for the kiln's current with a documented margin.
<<<
PRIORITY: M
VERIFICATION: I

[REQUIREMENT]
UID: HR-07
STATEMENT: >>>
The heat-enable output shall drive the safety contactor through a circuit that requires a **periodic software refresh** to hold the contactor closed, so that a hung or crashed MCU releases it ([LINK: SR-02]).
<<<
PRIORITY: M
VERIFICATION: I, T

[REQUIREMENT]
UID: HR-08
STATEMENT: >>>
All heater and contactor control outputs shall have external pull-downs to the de-energised state, and shall not use pins that are strapping pins or that glitch during reset or boot on the ESP32-S3.
<<<
PRIORITY: M
VERIFICATION: I, T

[REQUIREMENT]
UID: HR-09
STATEMENT: >>>
The system shall carry an **on-board** audible alarm: a 5 V active (self-driving) magnetic buzzer switched low-side from the alarm GPIO, so that annunciation needs no external component or field wiring.
<<<
PRIORITY: M
VERIFICATION: I

[REQUIREMENT]
UID: HR-19
STATEMENT: >>>
Every test point shall be a surface pad on the **top copper layer only**, so the whole board can be probed without turning it over or removing it from its enclosure. No test point shall be placed on the bottom layer.
<<<
PRIORITY: M
VERIFICATION: I

[REQUIREMENT]
UID: HR-20
STATEMENT: >>>
Test-point pads shall be small enough not to drive the board area, and shall carry no drilled hole. 1.5 mm square is the design value.
<<<
PRIORITY: S
VERIFICATION: I

[REQUIREMENT]
UID: HR-10
STATEMENT: >>>
Pin assignments shall be defined in one place per board variant and shall not be duplicated across the codebase.
<<<
PRIORITY: M
VERIFICATION: I

[REQUIREMENT]
UID: HR-11
STATEMENT: >>>
The design shall include a **current transformer (Stromwandler)** around one heater conductor, downstream of the safety contactor and the SSR, sized for the kiln's rated current with headroom, and preferably split-core so it can be fitted without breaking the heater wiring.
<<<
PRIORITY: M
VERIFICATION: I

[REQUIREMENT]
UID: HR-16
STATEMENT: >>>
The current transformer shall be a **voltage-output type with an integral burden resistor**, or shall have a burden resistor permanently fitted at the board. A current-output CT whose burden can be disconnected shall not be used, because an open secondary carrying primary current develops dangerous voltages.
<<<
PRIORITY: M
VERIFICATION: I

[REQUIREMENT]
UID: HR-17
STATEMENT: >>>
The CT input shall be conditioned for a single-supply ADC: mid-rail bias, anti-alias filtering matched to the sample rate of [LINK: FR-CUR-03], and clamping to the ADC supply rails.
<<<
PRIORITY: M
VERIFICATION: I

[REQUIREMENT]
UID: HR-18
STATEMENT: >>>
The CT provides the only galvanic isolation between the heater circuit and the controller electronics; its insulation rating and the creepage and clearance around its input shall be appropriate to the mains voltage in use.
<<<
PRIORITY: M
VERIFICATION: I

[REQUIREMENT]
UID: HR-12
STATEMENT: >>>
The design shall support an optional second SSR channel for a kiln with independently switched element groups.
<<<
PRIORITY: C
VERIFICATION: I

[REQUIREMENT]
UID: HR-13
STATEMENT: >>>
The installation shall include a hardware over-temperature cutout in the safety chain that operates independently of this controller.
<<<
PRIORITY: M
VERIFICATION: I

[REQUIREMENT]
UID: HR-24
STATEMENT: >>>
The thermocouple front ends' **`FAULT` outputs shall interrupt the contactor coil in hardware**, each through its own series switching element, so that a reported sensor fault removes the heater without the firmware taking part. Each `FAULT` net shall retain its own test point. The limits of this interlock shall be documented: the outputs are open-drain, so an **unpowered or absent** front end leaves the path closed, and the MAX31856 detects an open circuit only once its fault mask has been configured. The hardware interlock therefore covers faults the device actively reports, and [LINK: SR-04] in firmware remains the cover for a dead or unconfigured front end.
<<<
PRIORITY: M
VERIFICATION: I, T

[REQUIREMENT]
UID: HR-21
STATEMENT: >>>
Where a door or lid interlock is fitted, its switch shall be **normally closed** and shall be wired **both** into a controller input ([LINK: SR-31]) **and** in series with the safety contactor coil, so that opening the door de-energises the heater through hardware whether or not the firmware is working. The controller input provides annunciation, latching and logging; it is not the interlock.
<<<
PRIORITY: S
VERIFICATION: I, T

[REQUIREMENT]
UID: HR-25
STATEMENT: >>>
The contactor coil's freewheel diode shall be connected **across the coil itself**, on the kiln side of every series interrupting element of [LINK: HR-21] and [LINK: HR-24], so that opening any of them leaves the coil current a path to decay through. A freewheel path referenced to the raw supply instead would put the inductive transient across the opening contacts, eroding the lid switch and stressing the sense divider.
<<<
PRIORITY: M
VERIFICATION: I

[REQUIREMENT]
UID: HR-14
STATEMENT: >>>
The controller electronics shall be supplied from a regulated source able to power the MCU, display and contactor coil simultaneously, and shall not rely on a USB host for operating power.
<<<
PRIORITY: M
VERIFICATION: I

[REQUIREMENT]
UID: HR-15
STATEMENT: >>>
Thermocouple inputs shall be filtered and protected at the hardware level against the electrical noise of a switching multi-kilowatt load.
<<<
PRIORITY: M
VERIFICATION: I

[[/SECTION]]

[[SECTION]]
UID: SECT-7
TITLE: 7. Testability requirements

[TEXT]
STATEMENT: >>>
> "Designed for testability" is a stated goal of this project, so it is specified
> as requirements rather than left to implementation taste. The architecture in
> [`architecture.md`](architecture.md) is structured to satisfy this section.
<<<

[[SECTION]]
UID: SECT-7-1
TITLE: 7.1 Design for test

[REQUIREMENT]
UID: TR-01
STATEMENT: >>>
The control, safety, setpoint-generation, autotune, program, and log-encoding logic shall be implemented in components that contain **no reference to any hardware peripheral, ESP-IDF driver, or RTOS primitive**, and shall be compilable and runnable on a development host.
<<<
PRIORITY: M
VERIFICATION: A, I

[REQUIREMENT]
UID: TR-02
STATEMENT: >>>
All hardware access shall be reached through explicit HAL interfaces that can be substituted at link or construction time by a test double.
<<<
PRIORITY: M
VERIFICATION: I

[REQUIREMENT]
UID: TR-03
STATEMENT: >>>
No logic component shall read a clock directly; time shall be supplied through an injected time source, so that a 24 h firing can be simulated in milliseconds.
<<<
PRIORITY: M
VERIFICATION: A, I

[REQUIREMENT]
UID: TR-04
STATEMENT: >>>
Logic components shall be free of global mutable state: each shall operate on an explicit context passed by the caller, so that multiple independent instances can coexist in one test process.
<<<
PRIORITY: M
VERIFICATION: I

[REQUIREMENT]
UID: TR-05
STATEMENT: >>>
Logic components shall perform no dynamic allocation after initialisation, and their memory footprint shall be statically determinable.
<<<
PRIORITY: S
VERIFICATION: A

[REQUIREMENT]
UID: TR-06
STATEMENT: >>>
Every component shall have a declared, minimal public interface; no test shall need access to a private symbol to verify required behaviour.
<<<
PRIORITY: M
VERIFICATION: I

[REQUIREMENT]
UID: TR-07
STATEMENT: >>>
Component dependencies shall be acyclic and shall respect the layering of [`architecture.md`](architecture.md); a violation shall fail the build.
<<<
PRIORITY: M
VERIFICATION: A

[REQUIREMENT]
UID: TR-08
STATEMENT: >>>
The state of the run controller and the safety supervisor shall be fully observable through a query interface, so that tests assert on state rather than on side effects.
<<<
PRIORITY: M
VERIFICATION: I

[REQUIREMENT]
UID: TR-09
STATEMENT: >>>
Every fault condition of §5.2 ([LINK: SECT-5-2]) shall be reachable in a test through a documented stimulus, without physical hardware.
<<<
PRIORITY: M
VERIFICATION: T

[REQUIREMENT]
UID: TR-10
STATEMENT: >>>
Test-only interfaces (fault injection, state forcing, time warping) shall be compiled out of production builds, verified by a build-time check.
<<<
PRIORITY: M
VERIFICATION: A

[[/SECTION]]

[[SECTION]]
UID: SECT-7-2
TITLE: 7.2 Test infrastructure

[REQUIREMENT]
UID: TR-11
STATEMENT: >>>
The project shall provide a **kiln plant simulator**: a first-order-plus-dead-time thermal model with configurable gain, time constant, dead time, ambient temperature and noise, capable of injected faults (open element, shorted SSR, open TC, drifting TC, lid opened).
<<<
PRIORITY: M
VERIFICATION: I, T

[REQUIREMENT]
UID: TR-12
STATEMENT: >>>
The simulator shall be deterministic and reproducible from a seed, so that a failing test can be replayed exactly.
<<<
PRIORITY: M
VERIFICATION: T

[REQUIREMENT]
UID: TR-13
STATEMENT: >>>
The project shall provide host-executed unit tests for every logic component, runnable with a single command and without hardware.
<<<
PRIORITY: M
VERIFICATION: D

[REQUIREMENT]
UID: TR-14
STATEMENT: >>>
The project shall provide closed-loop integration tests that run the real control, setpoint, safety and autotune code against the simulator, verifying the performance requirements [LINK: NFR-05] to [LINK: NFR-08] and the safety reactions of §5 ([LINK: SECT-5]).
<<<
PRIORITY: M
VERIFICATION: T

[REQUIREMENT]
UID: TR-15
STATEMENT: >>>
The project shall provide on-target tests for the HAL drivers, run on real hardware or an emulator, covering front-end configuration and fault decoding, display output, encoder decoding, storage and the time-proportional output.
<<<
PRIORITY: M
VERIFICATION: T

[REQUIREMENT]
UID: TR-16
STATEMENT: >>>
The project shall provide API-level tests that exercise the HTTP interface end-to-end against a firmware instance, including malformed and hostile input.
<<<
PRIORITY: M
VERIFICATION: T

[REQUIREMENT]
UID: TR-17
STATEMENT: >>>
The project shall provide a documented HIL procedure using a low-power resistive load and a thermocouple simulator, for the tests that cannot be virtualised.
<<<
PRIORITY: S
VERIFICATION: I

[REQUIREMENT]
UID: TR-18
STATEMENT: >>>
Timing requirements [LINK: NFR-01] to [LINK: NFR-04] shall be verified on target by instrumented measurement of cycle period, jitter and worst-case latency, reported as numbers rather than asserted by inspection.
<<<
PRIORITY: M
VERIFICATION: T

[REQUIREMENT]
UID: TR-19
STATEMENT: >>>
The project shall measure line and branch coverage of host tests and shall achieve at least **90 % line coverage** of the control, safety, setpoint, program and autotune components, and **100 % of safety decision branches**.
<<<
PRIORITY: M
VERIFICATION: A

[REQUIREMENT]
UID: TR-20
STATEMENT: >>>
The build shall support address and undefined-behaviour sanitisers for host test runs.
<<<
PRIORITY: S
VERIFICATION: A

[REQUIREMENT]
UID: TR-21
STATEMENT: >>>
Long-duration behaviour ([LINK: NFR-10], [LINK: NFR-11]) shall be verifiable both by accelerated simulation and by an automated soak test on target.
<<<
PRIORITY: M
VERIFICATION: T

[[/SECTION]]

[[SECTION]]
UID: SECT-7-3
TITLE: 7.3 Process

[REQUIREMENT]
UID: TR-22
STATEMENT: >>>
Every requirement in this document shall be traceable to at least one verification artefact, and the traceability shall be maintained as a machine-checkable file in the repository.
<<<
PRIORITY: M
VERIFICATION: A

[REQUIREMENT]
UID: TR-23
STATEMENT: >>>
Every requirement in §5 ([LINK: SECT-5]) shall be covered by at least one **automated** test; inspection alone shall not be sufficient.
<<<
PRIORITY: M
VERIFICATION: A

[REQUIREMENT]
UID: TR-24
STATEMENT: >>>
Continuous integration shall, on every push and pull request: build the firmware, run all host unit and integration tests with coverage, run static analysis, run the emulated target and API tests, and lint the web assets. A failure in any of these shall block merge.
<<<
PRIORITY: M
VERIFICATION: I

[REQUIREMENT]
UID: TR-25
STATEMENT: >>>
A defect fix shall be accompanied by a regression test that fails before the fix and passes after it.
<<<
PRIORITY: M
VERIFICATION: I

[REQUIREMENT]
UID: TR-26
STATEMENT: >>>
Test names shall reference the requirement identifiers they verify.
<<<
PRIORITY: S
VERIFICATION: I

[REQUIREMENT]
UID: TR-27
STATEMENT: >>>
The kiln plant simulator ([LINK: TR-11]) shall model heater current as well as temperature, and shall inject the electrical faults that [LINK: SR-25]–[LINK: SR-30] detect: relay fail-on, relay fail-off, welded contactor (current persisting after the contactor is commanded open), partial element failure, over-current, and a disconnected current transformer.
<<<
PRIORITY: M
VERIFICATION: T

[REQUIREMENT]
UID: TR-28
STATEMENT: >>>
The HIL jig ([LINK: TR-17]) shall be able to present a known current to the transformer and to emulate a welded contactor, so that the discrimination sequence of [LINK: SR-27] is verified against real hardware and not only in simulation.
<<<
PRIORITY: M
VERIFICATION: I

[REQUIREMENT]
UID: TR-29
STATEMENT: >>>
The independent safety supervisor's trip logic and the link's wire format shall achieve at least **80 % modified condition/decision coverage (MC/DC)** in host tests, measured and enforced automatically.

Line and branch coverage are insufficient for this component, and the reason is specific rather than general. Its permit decision is a five-term conjunction, and a single test with every term true plus one with every term false gives 100 % line and 100 % branch coverage of that decision while demonstrating none of what matters: that a missing reading alone withholds heat, that a reported fault alone withholds heat, and so on for each term independently. MC/DC is the criterion that requires each condition to be shown to change the outcome on its own.

This applies to the supervisor and not to the rest of the firmware. It is about 120 lines of logic, it is the only component in which failing to evaluate a condition means heat that should have stopped, and it is the component whose entire justification is that it can be read and verified in full ([LINK: AD-22]).
<<<
PRIORITY: M
VERIFICATION: T

[[/SECTION]]

[[/SECTION]]

[[SECTION]]
UID: SECT-8
TITLE: 8. Constraints

[CONSTRAINT]
UID: CON-01
STATEMENT: >>>
The firmware shall be built with **ESP-IDF v5.x** and its native build system. The Arduino framework shall not be used.
<<<

[CONSTRAINT]
UID: CON-02
STATEMENT: >>>
The target is the **ESP32-S3**. Nothing in the design shall depend on a feature absent from that part.
<<<

[CONSTRAINT]
UID: CON-03
STATEMENT: >>>
Logged data and programs shall live on internal flash. **No SD card** shall be required, and **no external database** or network service shall be required for any function.
<<<

[CONSTRAINT]
UID: CON-04
STATEMENT: >>>
The project shall be licensed **GPL-3.0-or-later**, and every third-party component shall carry a licence compatible with distribution under GPL-3.0. Web assets shall be vendored, not fetched at build time from an unpinned source.
<<<

[CONSTRAINT]
UID: CON-05
STATEMENT: >>>
Implementation language shall be C or C++ as supported by ESP-IDF; the logic components of [LINK: TR-01] shall be written so as to be compilable by a host toolchain without ESP-IDF headers.
<<<

[CONSTRAINT]
UID: CON-06
STATEMENT: >>>
The web interface shall run in current versions of Firefox, Chrome and Safari, including on mobile, without a build step that requires a network connection at build time.
<<<

[CONSTRAINT]
UID: CON-07
STATEMENT: >>>
Total bill of materials for the controller electronics should remain comparable to the reference design of [R1] (order of 40 EUR), excluding the SSR, contactor and enclosure.
<<<

[[/SECTION]]

[[SECTION]]
UID: SECT-9
TITLE: 9. Assumptions

[ASSUMPTION]
UID: ASM-01
STATEMENT: >>>
The kiln is a resistively heated electric kiln whose thermal response is adequately described by a first-order-plus-dead-time model over the operating range.
<<<

[ASSUMPTION]
UID: ASM-02
STATEMENT: >>>
The kiln has a single thermal zone. Multi-zone kilns are out of scope for v1.0 but the architecture shall not preclude them.
<<<

[ASSUMPTION]
UID: ASM-03
STATEMENT: >>>
The heating elements are switched by a zero-cross SSR; the controller does not perform phase-angle control.
<<<

[ASSUMPTION]
UID: ASM-04
STATEMENT: >>>
A competent person performs the mains installation, and an independent over-temperature cutout is fitted ([LINK: HR-13]).
<<<

[ASSUMPTION]
UID: ASM-05
STATEMENT: >>>
The device is on a trusted local network ([LINK: NFR-20]).
<<<

[ASSUMPTION]
UID: ASM-06
STATEMENT: >>>
The operator is present in the building during firing, as kiln manufacturers require. Unattended firing is not a design goal.
<<<

[ASSUMPTION]
UID: ASM-07
STATEMENT: >>>
Wall-clock time may be unavailable; all timing-critical behaviour uses the monotonic time base ([LINK: FR-NET-08]).
<<<

[ASSUMPTION]
UID: ASM-08
STATEMENT: >>>
Internal flash endurance is at least 100 000 erase cycles per block.
<<<

[ASSUMPTION]
UID: ASM-09
STATEMENT: >>>
The heater load is resistive and switched as a single group, so the current in the monitored conductor is proportional to total heater power.
<<<

[ASSUMPTION]
UID: ASM-10
STATEMENT: >>>
The kiln is **single phase**. Three-phase kilns are out of scope (§12 ([LINK: SECT-12]), [LINK: OQ-06]), so there is no unmonitored phase for a fault to hide on: there is one phase and one current transformer on it ([LINK: HR-11]).
<<<

[[/SECTION]]

[[SECTION]]
UID: SECT-10
TITLE: 10. Verification strategy summary

[TEXT]
STATEMENT: >>>
| Level | What it covers | Where it runs |
|---|---|---|
| **Unit** | Individual logic components: PID maths, setpoint generator, program validation, autotune identification, safety rules, log codec, config validation. | Host |
| **Integration (simulated)** | Closed-loop behaviour of the real firmware logic against the kiln simulator ([LINK: TR-11]): control performance, full program execution, every fault scenario, autotune convergence, power-loss recovery. | Host |
| **Driver / on-target** | HAL against real silicon: MAX31856 configuration and fault decode, OLED, encoder, flash log store, time-proportional output timing. | Target / emulator |
| **API** | HTTP endpoints, authentication, input validation, push updates, decimation correctness, hostile input. | Target / emulator |
| **Timing** | Loop period, jitter, safety latency, boot time, under load. | Target, instrumented |
| **Soak** | 168 h run, heap stability, log wraparound, WiFi reconnection. | Target |
| **Current / relay fault** | Every rule of [LINK: SR-25]–[LINK: SR-30] against the simulator's electrical fault injections, including the full weld-discrimination sequence. | Host |
| **HIL** | Output stage, contactor watchdog release, real thermocouple, real SSR with resistive load, real CT with a known current, emulated welded contactor. | Bench jig |
| **Commissioning** | Autotune and a full firing on a real kiln. | Real kiln |
<<<

[[/SECTION]]

[[SECTION]]
UID: SECT-11
TITLE: 11. Open questions

[QUESTION]
UID: OQ-01
STATEMENT: >>>
Should cone-based targets (Orton cone numbers with heatwork/rate correction) be offered in addition to plain temperature targets?
<<<

[QUESTION]
UID: OQ-02
STATEMENT: >>>
**Resolved 2026-09-28: yes.** The current transformer is mandatory ([LINK: HR-11]) and drives FR-CUR ([LINK: SECT-3-12]) and [LINK: SR-25]–[LINK: SR-30]. The thermal detections are retained as an independent backstop.
<<<
STATUS: Resolved

[QUESTION]
UID: OQ-06
STATEMENT: >>>
**Resolved 2026-10-06: single phase only.** Three-phase kilns are out of scope (§12 ([LINK: SECT-12])). A three-phase kiln monitored on one phase is worse than one not supported at all: a fault on an unmonitored phase would be caught only by the thermal rules, slowly, and the power and energy figures would cover a third of the load while looking like a whole-kiln number. This reverses the resolution of 2026-10-05 and reinstates [LINK: ASM-10] in a narrower form.
<<<
STATUS: Resolved

[QUESTION]
UID: OQ-08
STATEMENT: >>>
What replaces the removed over-the-web firmware update ([LINK: FR-UPD-01])? USB/serial via `esptool`, an image staged over the network but applied only after a physical confirmation at the kiln, or no field update at all? The device currently has **no update path**, so this blocks release rather than merely being open.
<<<

[QUESTION]
UID: OQ-09
STATEMENT: >>>
Where are firing programs authored, now that [LINK: FR-WEB-26] has made the web interface read-only? A local editor on a rotary encoder and a 128x64 display is possible but unpleasant; importing from a file on first boot, or shipping only the examples of [LINK: FR-PRG-09], are the alternatives. Until this is answered a user cannot create a curve of their own, which is a real functional gap rather than a nicety.
<<<

[QUESTION]
UID: OQ-07
STATEMENT: >>>
Should the element positive temperature coefficient used to correct the [LINK: SR-28] baseline be measured automatically during the first firing, or entered by the installer from the element datasheet?
<<<

[QUESTION]
UID: OQ-03
STATEMENT: >>>
Should the log store be sized for whole-life retention of run summaries in a separate, non-circular area?
<<<

[QUESTION]
UID: OQ-04
STATEMENT: >>>
Which small charting approach for [LINK: FR-WEB-06], a vendored MIT-licensed micro-library, or hand-written canvas rendering? Decided in the architecture, revisit if asset budget is exceeded.
<<<

[QUESTION]
UID: OQ-05
STATEMENT: >>>
Is a 3-zone variant ([LINK: ASM-02]) a v1.1 goal? It affects whether the control component is written for one zone or N from the start.
<<<

[[/SECTION]]

[[SECTION]]
UID: SECT-12
TITLE: 12. Out of scope

[TEXT]
STATEMENT: >>>
- Phase-angle or PWM mains modulation; only zero-cross SSR switching.
- Multi-zone control in v1.0 ([LINK: ASM-02]).
- **Three-phase kilns.** Decided 2026-10-06 ([LINK: OQ-06]). Monitoring one phase of three would leave a fault on either of the others to the thermal rules alone, and would report a third of the load as though it were the whole, so partial support is worse than none.
- Cloud connectivity, remote access outside the local network, mobile apps.
- Safety certification, or replacement of the hardware over-temperature cutout.
- Atmosphere, damper, oxygen or gas control; kiln venting hardware.
- Kiln power wiring, contactor sizing and enclosure design (documented in `hardware/`, not specified here).
- Firing-recipe advice; the device executes curves, it does not author them.
<<<

[[/SECTION]]

[[SECTION]]
UID: SECT-APPENDIX-A-FAULT-CODE-ALLOCATION
TITLE: Appendix A, Fault code allocation

[TEXT]
STATEMENT: >>>
Codes are stable and shall not be reused. Detail in §5.2 ([LINK: SECT-5-2]).

| Code | Fault | Requirement |
|---|---|---|
| 1 | Chamber thermocouple open circuit | SR-04 |
| 2 | Chamber thermocouple short circuit | SR-04 |
| 3 | Chamber reading out of range | SR-04 |
| 4 | Cold-junction fault | SR-04 |
| 5 | Front-end communication failure | SR-04 |
| 6 | Chamber thermocouple reversed | SR-05 |
| 7 | Chamber sensor stuck | SR-06 |
| 8 | Thermal runaway / heating failure | SR-07 |
| 9 | Uncommanded heating (SSR shorted) | SR-08 |
| 10 | Over-temperature | SR-09 |
| 11 | Setpoint excursion | SR-10 |
| 12 | Enclosure over-temperature | SR-11 |
| 13 | Control loop deadline missed | SR-13 |
| 14 | Safety supervisor deadline missed | SR-13 |
| 15 | Watchdog reset during run | SR-14 |
| 16 | Enclosure thermocouple fault | SR-04, SR-11 |
| 17 | Operator abort | FR-RUN-04 |
| 18 | Autotune failed to converge | FR-TUN-07 |
| 19 | Power-loss recovery refused | FR-RUN-08 |
| 20 | Configuration invalid / storage failure | FR-CFG-05 |
| 21 | Uncommanded heater current (relay fail-on) | SR-25 |
| 22 | Contactor welded, isolate at the supply | SR-27 |
| 23 | No heater current when commanded (relay/element fail-off) | SR-26 |
| 24 | Heater current deviation (partial element failure) | SR-28 |
| 25 | Heater over-current | SR-29 |
| 26 | Current transformer fault or disconnected | FR-CUR-11 |
| 27 | Door opened during a firing | SR-31 |

Warnings (non-latching, do not stop a firing):

| Code | Warning | Requirement |
|---|---|---|
| 101 | Insulation degradation suspected | SR-12 |
| 102 | Hold-back active, firing behind schedule | FR-CTL-11 |
| 103 | Log store unavailable | FR-LOG-14 |
| 104 | Display unavailable | FR-HMI-14 |
| 105 | Time not synchronised | FR-LOG-12 |
| 106 | WiFi disconnected | FR-NET-07 |
| 107 | Duty saturated for extended period | FR-CTL-15 |
| 108 | Gains are untuned defaults | FR-TUN-11 |
| 109 | Relay switching-operation life limit reached | SR-30 |
| 110 | Intermittent current mismatch, a relay may be failing | SR-30 |
| 111 | Current monitoring disabled | FR-CUR-12 |
| 112 | Heater current deviating from the run reference | SR-28 |
| 113 | No door interlock fitted | SR-31 |
<<<

[[/SECTION]]
