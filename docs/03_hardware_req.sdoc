[DOCUMENT]
TITLE: Safe Kiln Controller, Hardware Requirements
UID: SAFEKILN-HWR
VERSION: 0.1 (draft)
DATE: 2026-10-29
OPTIONS:
  MARKUP: Markdown
  VIEW_STYLE: Table
  NODE_IN_TOC: True
METADATA:
  SPDX-FileCopyrightText: 2026 Bitcrush Testing
  SPDX-License-Identifier: GPL-3.0-or-later
  Status: For review
  Project: Safe Kiln Controller, PID kiln controller

[GRAMMAR]
ELEMENTS:
- TAG: TEXT
  FIELDS:
  - TITLE: STATEMENT
    TYPE: String
    REQUIRED: True
- TAG: REQUIREMENT
  FIELDS:
  - TITLE: UID
    TYPE: String
    REQUIRED: True
  - TITLE: TITLE
    TYPE: String
    REQUIRED: False
  - TITLE: STATEMENT
    TYPE: String
    REQUIRED: True
  - TITLE: PRIORITY
    TYPE: SingleChoice(M, S, C)
    REQUIRED: False
  - TITLE: VERIFICATION
    TYPE: String
    REQUIRED: False
  RELATIONS:
  - TYPE: Parent
    ROLE: Refines

[TEXT]
STATEMENT: >>>
Level 3 of the V-model, the hardware branch, parallel to
[`03_software_req.sdoc`](03_software_req.sdoc). Both refine `SYS-`.

`SYS-HW-*` in [`02_system_req.sdoc`](02_system_req.sdoc) says what the system
needs: two switching devices in series, a buzzer, an interlock input. These
are the board-level consequences, with the numbers. A requirement is here when
getting it wrong is a hardware change rather than a firmware one.

Verification: **I** inspection or review, **A** analysis or calculation,
**T** bench measurement, **H** on the HIL fixture.

Each item's open work is tracked in section A of
[`tasklist.md`](../tasklist.md); this document is what the board has to achieve,
not the list of fixes outstanding.
<<<

[[SECTION]]
UID: SECT-HW-1
TITLE: 1. Heat authority

[REQUIREMENT]
UID: HWR-01
TITLE: Charge-pump release inside one second
STATEMENT: >>>
The charge pump shall release the contactor within **1 s** of `HEAT_EN` ceasing to toggle, and shall pass through the MOSFET's linear region fast enough that the contactor cannot rest partially closed.

Present circuit: `HEAT_EN` → R19 → C23 (10 µF) → D5 (BAT54S) → `HEAT_EN_DC` → C24 (3.3 µF) ∥ R20 (47 k) → Q3 gate. Two numbers need establishing rather than assuming: the pumped level is about 3.3 V − 2·V<sub>f</sub> ≈ 2.7 V, below the 4.5 V at which the AO3400A's R<sub>DS(on)</sub> is specified; and decay is τ ≈ 155 ms, so release is a slide rather than an edge.

This is the circuit [LINK: SYS-SAF-02] rests on and the design's most fragile idea. If the margin is thin, a comparator or a retriggerable monostable buys a crisp threshold for a few cents.
<<<
PRIORITY: M
VERIFICATION: A, H
RELATIONS:
- TYPE: Parent
  VALUE: SYS-HW-07
  ROLE: Refines
- TYPE: Parent
  VALUE: SYS-SAF-02
  ROLE: Refines

[REQUIREMENT]
UID: HWR-02
TITLE: Outputs default to de-energised
STATEMENT: >>>
Every heater and contactor control output shall carry an external pull-down to the de-energised state, and shall avoid strapping pins and pins that glitch during reset.

The window this covers is reset to first instruction, where a GPIO is high-impedance and the net sits wherever the board leaks to.
<<<
PRIORITY: M
VERIFICATION: I, T
RELATIONS:
- TYPE: Parent
  VALUE: SYS-HW-08
  ROLE: Refines

[REQUIREMENT]
UID: HWR-03
TITLE: The supervisor's permit needs its own pull-down
STATEMENT: >>>
The supervisor's permit output is active high, so its series element shall have an external pull-down. Without one there is a window at every supervisor reset in which the element's state is whatever the board leaks to.
<<<
PRIORITY: M
VERIFICATION: I, T
RELATIONS:
- TYPE: Parent
  VALUE: SYS-HW-26
  ROLE: Refines

[REQUIREMENT]
UID: HWR-04
TITLE: Freewheel across the coil
STATEMENT: >>>
The coil's freewheel diode shall sit across the coil itself, on the kiln side of every series interrupting element, so opening any of them leaves the current a path to decay through.

Referenced to the raw supply instead, the inductive transient appears across the opening contacts and erodes the lid switch.

Present circuit: D6 (SS14, 1 A Schottky) from `COIL_DRV` to `LID_SWITCH`, directly across J8. It carries the full coil current for the length of the decay, which a 12 V contactor coil puts at a few hundred milliamps; the 1N4148W it replaced is rated 300 mA.
<<<
PRIORITY: M
VERIFICATION: I
RELATIONS:
- TYPE: Parent
  VALUE: SYS-HW-25
  ROLE: Refines

[REQUIREMENT]
UID: HWR-26
TITLE: Nothing bypasses the lid contact
STATEMENT: >>>
No component shall connect the supply side of the lid contact to the coil side. Indicators, sense networks and protection on the coil shall all be referenced to `LID_SWITCH`, the kiln side of the contact, or to `COIL_DRV`.

Present circuit: the COIL indicator, R21 (2.2 k) and D7, runs from `LID_SWITCH` to `COIL_DRV`, across the coil.

Until 2026-10-29 R21 was fed from the supply rail. With the lid open and both series elements off, current ran supply → R21 → D7 → `COIL_DRV` → D6 → `LID_SWITCH` → R30/R31 and put about 2 V on `LID_SENSE`, which is between the ESP32-S3's input thresholds. An open lid could read as shut, and `COIL_FEEDBACK` read high whatever the lid did. A few milliamps through an LED cannot pull a contactor in, so the hardware interlock held, but the two inputs that report on it did not.
<<<
PRIORITY: M
VERIFICATION: I, T
RELATIONS:
- TYPE: Parent
  VALUE: SYS-HW-21
  ROLE: Refines

[REQUIREMENT]
UID: HWR-27
TITLE: The lid sense reads both states with margin
STATEMENT: >>>
`LID_SENSE` shall read high with the lid shut at the lowest supply the design accepts, and shall stay inside the ESP32-S3 pin's absolute maximum at the highest, with the firmware's internal pull-down enabled as [LINK: SWR-SAF-31] configures it.

Present circuit: R30 (22 k) over R31 (10 k), with D10 (BAT54S) clamping the node to +3V3 and GND. The internal pull-down (about 45 kΩ) sits in parallel with R31 and brings the ratio to 0.27, which gives 2.98 V at 11 V and 3.25 V at 12 V against a V<sub>IH</sub> of 2.48 V. Without the pull-down, or above about 13 V, the clamp holds the pin near 3.6 V through 22 k, which is well under a milliamp into the 3V3 rail.

A divider alone cannot do this. The window between V<sub>IH</sub> and the absolute maximum is a factor of 1.45, which the supply tolerance and the spread of the internal pull-down use up between them.
<<<
PRIORITY: M
VERIFICATION: A, T
RELATIONS:
- TYPE: Parent
  VALUE: SYS-HW-21
  ROLE: Refines

[[/SECTION]]

[[SECTION]]
UID: SECT-HW-2
TITLE: 2. Temperature acquisition

[REQUIREMENT]
UID: HWR-05
TITLE: Separate buses for the two front ends
STATEMENT: >>>
Both chamber MAX31856 front ends shall be on the supervisor, each on its own SPI bus, as [LINK: SWR-SAF-37] requires. They shall share no `SCK`, `SDI`, `SDO`, chip select or `~FAULT` line with each other, and the controller shall be connected to none of them. `~DRDY` is not connected at all ([LINK: HWR-06]).

Present circuit: U3 (`TC1_*`) on PA4 to PA7 and U4 (`TC2_*`) on PB5 to PB8 of U5, with no ESP32 pin on either bus.

Two chip selects on one bus would make both readings depend on the same shift register and clock, so one failure there would take both couples at once. A controller pin on either bus would let a crashed controller with a pin latched disturb a reading the supervisor relies on, and the supervisor would no longer be independent of it.
<<<
PRIORITY: M
VERIFICATION: I
RELATIONS:
- TYPE: Parent
  VALUE: SYS-HW-02
  ROLE: Refines

[REQUIREMENT]
UID: HWR-06
TITLE: Fault outputs are pulled up, and DRDY is not connected
STATEMENT: >>>
Every MAX31856 `~FAULT` output shall carry an external pull-up to +3V3. It is open-drain and reads as asserted when floating. `~DRDY` shall not be connected, and nothing shall depend on it.

Present circuit: R36 (10 k) on `TC1_FAULT` and R37 (10 k) on `TC2_FAULT`, both to +3V3, beside U3 and U4. `~DRDY` on both parts carries a no-connect flag.

The supervisor also enables its internal pull-ups on PA3 and PB4, but those exist only once its firmware has configured the pins. The external resistors hold the lines through reset and boot, and for a supervisor that never gets that far.

`~DRDY` is not needed because the supervisor runs each part in continuous conversion and reads temperature and fault status in one burst, so it never waits on a conversion edge. At start-up it waits for the first conversion by reading the registers, not the pin. Unconnected, the pin is an open-drain output with nothing to pull it up and draws no current, which is why it gets no resistor either.

**Amended 2026-10-29.** This required pull-ups on `~DRDY` and `~FAULT` both, and the board had neither: `~FAULT` relied on the supervisor's internal pull-ups, and `~DRDY` was unconnected, where a pull-up would serve nothing because nothing reads it.
<<<
PRIORITY: M
VERIFICATION: I
RELATIONS:
- TYPE: Parent
  VALUE: SYS-HW-02
  ROLE: Refines

[REQUIREMENT]
UID: HWR-07
TITLE: Chip selects are defined through reset
STATEMENT: >>>
`TC1_CS` and `TC2_CS` shall be pulled to their idle level. Both float during reset and boot, and a chip select asserted by leakage starts a conversion nobody asked for.
<<<
PRIORITY: S
VERIFICATION: I
RELATIONS:
- TYPE: Parent
  VALUE: SYS-HW-08
  ROLE: Refines

[REQUIREMENT]
UID: HWR-08
TITLE: Thermocouple inputs are clamped
STATEMENT: >>>
The thermocouple inputs shall be clamped to the front end's supply rails, and `VBIAS` shall be decoupled.

A thermocouple is a multi-metre unshielded pair routed beside a switching multi-kilowatt load.

Present circuit: `VBIAS` is decoupled by C31 (10 µF) at the R24/R25 divider (10 k/10 k off +3V3), which before 2026-10-29 presented about 5 kΩ to the bias node with no local capacitance. The thermocouple inputs themselves have no clamp beyond the MAX31856's own input protection, so that half is open.
<<<
PRIORITY: M
VERIFICATION: I, T
RELATIONS:
- TYPE: Parent
  VALUE: SYS-HW-15
  ROLE: Refines

[[/SECTION]]

[[SECTION]]
UID: SECT-HW-3
TITLE: 3. Current measurement

[REQUIREMENT]
UID: HWR-09
TITLE: Full scale fits the ADC without clipping
STATEMENT: >>>
The CT front end shall put **60 A** ([LINK: SWR-CUR-02]'s full scale) at roughly **0.5 V<sub>rms</sub>** about the mid-rail bias, and the resulting LSB shall be recorded against the 0.1 A resolution the same requirement asks for.

J10 is annotated "CT 30 A/1 V". At 60 A that delivers 2 V<sub>rms</sub> = ±2.83 V<sub>pk</sub> about the 1.65 V bias: the clamp conducts and the reading saturates across the whole upper half of the required range. Even at 30 A the swing reaches 0.24 V to 3.06 V, where the ESP32-S3 ADC is least linear.
<<<
PRIORITY: M
VERIFICATION: A, T
RELATIONS:
- TYPE: Parent
  VALUE: SYS-HW-17
  ROLE: Refines

[REQUIREMENT]
UID: HWR-10
TITLE: The anti-alias filter is below Nyquist
STATEMENT: >>>
The CT anti-alias corner shall sit **below half the sample rate**. Pick the sample rate first, then the filter.

R26 (1 k) + C25 (220 nF) gives f<sub>c</sub> ≈ 723 Hz against a 1 kHz sample rate whose Nyquist is 500 Hz: the corner is above Nyquist and the filter does not anti-alias. Either 4–8 kHz sampling with a corner near 300 Hz, or a corner near 200 Hz for 1 kHz.
<<<
PRIORITY: M
VERIFICATION: A, T
RELATIONS:
- TYPE: Parent
  VALUE: SYS-HW-17
  ROLE: Refines

[REQUIREMENT]
UID: HWR-11
TITLE: An absent CT is electrically recognisable
STATEMENT: >>>
`CURR_SENSE` shall carry a defined bias that the CT winding cannot produce, so an open input is distinguishable from genuinely zero current.

With J10 open the node is held only by C25 and diode leakage, so it drifts. [LINK: SWR-CUR-11] has to tell those two cases apart and [LINK: SWR-CUR-12] refuses to start a run on the second.
<<<
PRIORITY: M
VERIFICATION: I, T
RELATIONS:
- TYPE: Parent
  VALUE: SYS-HW-17
  ROLE: Refines

[REQUIREMENT]
UID: HWR-12
TITLE: The clamp holds the ADC inside its absolute maximum
STATEMENT: >>>
The CT node shall be clamped to within the ADC pin's absolute maximum of −0.3 V to V<sub>DD</sub>+0.3 V, through a series resistor that limits clamp current.

A **Schottky** clamp is required rather than preferred: at 1 mA a BAT54S drops about 0.32 V and holds the node near 3.6 V, while a silicon diode's 0.7 V would hold it at 4.0 V and exceed the pin's rating by 0.4 V. D9 is a BAT54S, which is correct; what is open is the scaling of [LINK: HWR-09], which currently drives the clamp during normal operation.
<<<
PRIORITY: M
VERIFICATION: A, I
RELATIONS:
- TYPE: Parent
  VALUE: SYS-HW-17
  ROLE: Refines

[REQUIREMENT]
UID: HWR-13
TITLE: The CT is specified on the schematic
STATEMENT: >>>
The CT's required characteristics shall appear as a schematic note, and no CT-related part shall be annotated "(opt)" without the behaviour of its absence being defined.

A split-core CT fitted to the wrong conductor reads a current that is real and not the heater's.
<<<
PRIORITY: S
VERIFICATION: I
RELATIONS:
- TYPE: Parent
  VALUE: SYS-HW-16
  ROLE: Refines

[[/SECTION]]

[[SECTION]]
UID: SECT-HW-4
TITLE: 4. Power and protection

[REQUIREMENT]
UID: HWR-14
TITLE: The +12 V rail is budgeted, and coil faults do not reach the MCU
STATEMENT: >>>
The +12 V rail shall be budgeted for the contactor coil, the buzzer, the SSR drive and the logic regulator together. Neither coil inrush nor a short in the lid or coil wiring shall be able to brown out the MCU.

The coil is the largest and least constant load on the board, and the one that switches while a kiln is at temperature. Its wiring leaves the board twice, to the lid switch and to the contactor, and either run can be chafed against an earthed kiln case.

Present circuit: J1 → F1 (PTC, 1.1 A hold, 16 V) → D1 (SS34, reverse polarity) → +12V. The lid and coil branch is fed from +12V through its own F2 (PTC, 0.5 A hold, 15 V) to J9, so a short in that wiring trips F2 and leaves F1, the rail and the regulator where they were. F2's hold current has to sit above the fitted contactor's coil current, which is not yet fixed; 0.5 A covers a coil up to about 0.4 A.
<<<
PRIORITY: M
VERIFICATION: A, T
RELATIONS:
- TYPE: Parent
  VALUE: SYS-HW-05
  ROLE: Refines

[REQUIREMENT]
UID: HWR-15
TITLE: The regulator has dropout and thermal margin
STATEMENT: >>>
The 3V3 regulator shall hold regulation at the lowest input the design accepts, with its junction temperature inside its rating at full load and the highest specified ambient.

Present circuit: U2 (TPS54202, synchronous buck, 4.5 V to 28 V in, 2 A) from +12V, with L1 (10 µH, SWPA5040S), C2 (10 µF) and C30 (100 nF) at the input, C3 and C29 (2 × 22 µF) at the output, and R34/R35 (100 k/22.1 k) setting 3.29 V. `EN` is left open, which the part's internal pull-up enables.

Dropout is no longer the question it was: the lowest input is 12 V less tolerance, D1 and F1, around 10.5 V, against 4.5 V. What remains to check is the thermal case and the output ripple under the ESP32-S3's radio bursts. The AMS1117 this replaced dropped 8.7 V linearly at 12 V in, which is 2.6 W at 300 mA in a SOT-223.
<<<
PRIORITY: M
VERIFICATION: A
RELATIONS:
- TYPE: Parent
  VALUE: SYS-HW-05
  ROLE: Refines

[REQUIREMENT]
UID: HWR-16
TITLE: Input transients are clamped
STATEMENT: >>>
`V_IN` shall have transient protection. The fuse and series diode cover overcurrent and reverse polarity; neither clamps a surge, and the board sits next to a switching multi-kilowatt load.

Present circuit: D11 (SMBJ15CA, bidirectional) on `V_FUSED`, after F1 so that a sustained overvoltage trips the PTC rather than the TVS. It stands off 15 V and clamps at 24.4 V at 24.6 A, below U2's 28 V and C1's 25 V.
<<<
PRIORITY: S
VERIFICATION: I
RELATIONS:
- TYPE: Parent
  VALUE: SYS-HW-05
  ROLE: Refines

[REQUIREMENT]
UID: HWR-17
TITLE: USB is protected and decoupled
STATEMENT: >>>
`USB_DP`/`USB_DN` shall have low-capacitance ESD protection, and `VBUS` shall power nothing on the board ([LINK: SYS-HW-14]).

Present circuit: U6 (USBLC6-2SC6) on both lines next to J2. `VBUS` is unconnected at J2 and at U6 pin 5; the USBLC6's internal clamp still returns a positive strike to ground with that pin open.

**Amended 2026-10-29.** This asked for `VBUS` to be decoupled, when `VBUS` was still OR'd onto the supply. With USB data only, there is nothing on it to decouple.
<<<
PRIORITY: S
VERIFICATION: I
RELATIONS:
- TYPE: Parent
  VALUE: SYS-HW-05
  ROLE: Refines

[[/SECTION]]

[[SECTION]]
UID: SECT-HW-5
TITLE: 5. Operator interface and boot

[REQUIREMENT]
UID: HWR-18
TITLE: Boot-mode and encoder inputs are defined
STATEMENT: >>>
`MCU_IO0` shall have an external pull-up, and the encoder inputs shall have a defined network whose time constant is compatible with the quadrature decoder's expectations.

IO0 is pulled to ground by SW2 with nothing holding it otherwise; R10–R12 with C20–C22 need their corner checked against the knob's fastest realistic rotation.
<<<
PRIORITY: S
VERIFICATION: I, T
RELATIONS:
- TYPE: Parent
  VALUE: SYS-HW-04
  ROLE: Refines

[REQUIREMENT]
UID: HWR-19
TITLE: The supervisor's programming interface is reachable
STATEMENT: >>>
The supervisor's SWD pins shall come out to test points rather than being left as pads, and the clear button of [LINK: SYS-HW-28] shall be wired to the supervisor and to nothing else.

The independence argument rests on that firmware being reviewable and flashable on its own.

Present circuit: `SW_DIO`, `SW_CLK` and `SUPERVISOR_RESET` reach J4 (Tag-Connect TC2030), with `SUPERVISOR_RESET` on U5 pin 6 (PF2/`NRST`). The clear button is SW4 on `SUP_CLEAR`, U5 pin 7 (PA0), to GND, with TP39 on the same net.

Until 2026-10-29 the reset net went to PA0 and pin 6 was left open, so the debugger could not reset the supervisor and SW1 reset the ESP32-S3 alone, and there was no clear button at all.
<<<
PRIORITY: M
VERIFICATION: I
RELATIONS:
- TYPE: Parent
  VALUE: SYS-HW-26
  ROLE: Refines

[REQUIREMENT]
UID: HWR-20
TITLE: Test points survive the chain they outlived
STATEMENT: >>>
Each thermocouple `~FAULT` net shall retain its own test point, and the coil drive and permit nets shall each have one.

The discrete fault chain is superseded ([LINK: SYS-HW-24]); the test points cost nothing and are how a front end is diagnosed on a bench.
<<<
PRIORITY: S
VERIFICATION: I
RELATIONS:
- TYPE: Parent
  VALUE: SYS-HW-24
  ROLE: Refines

[REQUIREMENT]
UID: HWR-24
TITLE: The board has mounting holes
STATEMENT: >>>
The PCB shall carry **four M3 mounting holes**, 4 mm in from each corner of the 100 × 70 outline, plated or with keep-out to the nearest copper.

There are none today. Nothing fixes the board to anything, so the enclosure's standoffs ([`hardware/enclosure`](../hardware/enclosure/README.md)) are a proposal the board has to adopt rather than a fit to something that exists. A controller held in place by its own wiring is a controller whose terminal blocks take the weight of the loom.

The positions are the enclosure's, not the other way round, because the enclosure is printed from a parameterised model and the board is not.
<<<
PRIORITY: M
VERIFICATION: I
RELATIONS:
- TYPE: Parent
  VALUE: SYS-HW-05
  ROLE: Refines

[REQUIREMENT]
UID: HWR-25
TITLE: Every footprint is inside the outline
STATEMENT: >>>
Every footprint shall sit inside the board outline, and the placement shall be reviewed against it before routing continues.

**14 of 125 do not**, measured 2026-10-11 against the `gr_rect` at 50,40 to 150,110: `U4` (the second MAX31856) at y = 117.9 and `J7` (the second thermocouple terminal) at y = 73.2 are the two that matter, with a cluster of decoupling capacitors and test points beside them. A part outside the outline is not placed at all: it will not be fabricated where it appears, and the netlist that routes to it is routing into free space.
<<<
PRIORITY: M
VERIFICATION: I
RELATIONS:
- TYPE: Parent
  VALUE: SYS-HW-10
  ROLE: Refines

[[/SECTION]]

[[SECTION]]
UID: SECT-HW-6
TITLE: 6. Documentation and review

[REQUIREMENT]
UID: HWR-21
TITLE: One pin map, generated
STATEMENT: >>>
There shall be a single pin-map artefact, derived from the schematic rather than maintained beside it, covering both microcontrollers.

Pin assignments currently live in the schematic, in `board_pins.h` and in the supervisor's README, which is three places that can disagree.
<<<
PRIORITY: M
VERIFICATION: I
RELATIONS:
- TYPE: Parent
  VALUE: SYS-HW-10
  ROLE: Refines

[REQUIREMENT]
UID: HWR-22
TITLE: ERC is clean or its exclusions are recorded
STATEMENT: >>>
Electrical rule check shall pass, and every exclusion shall carry its reason in the project file.

There are none at present: ERC reported no violations on 2026-10-29 and `erc_exclusions` in `safekiln.kicad_pro` is empty. The shared SPI `SDO` exclusion this once expected went away when [LINK: HWR-05] put the two front ends on separate buses.
<<<
PRIORITY: M
VERIFICATION: I
RELATIONS:
- TYPE: Parent
  VALUE: SYS-HW-10
  ROLE: Refines

[REQUIREMENT]
UID: HWR-23
TITLE: Mains-adjacent routing is reviewed before fabrication
STATEMENT: >>>
The coil interrupt and every mains-adjacent net shall be reviewed for clearance and creepage before a board is ordered. The PCB currently has no tracks at all, so this is a requirement on work not yet done rather than a check on work done.
<<<
PRIORITY: M
VERIFICATION: I
RELATIONS:
- TYPE: Parent
  VALUE: SYS-HW-05
  ROLE: Refines

[[/SECTION]]
